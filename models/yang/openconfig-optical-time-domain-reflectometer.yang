module openconfig-optical-time-domain-reflectometer {

  yang-version "1";

  // namespace
  namespace "http://openconfig.net/yang/optical-time-domain-reflectometer";

  prefix "oc-otdr";

  // import some basic types
  import openconfig-platform { prefix oc-platform; }
  import openconfig-platform-types { prefix oc-platform-types; }
  import openconfig-extensions { prefix oc-ext; }
  import openconfig-yang-types { prefix oc-yang; }
  import openconfig-transport-types { prefix oc-opt-types; }


  // meta
  organization "OpenConfig working group";

  contact
    "OpenConfig working group
      www.openconfig.net";

  description
    "This model describes configuration and operational state data
    for an OTDR.";

  oc-ext:openconfig-version 0.1.3;

  revision 2020-04-01 {
    description
      "add otdr locator when sending rpc, modify ieee float-32 format to decimal64";
    reference "0.6.0";
  }

  revision "2019-04-28" {
    description
      "Update otdr result categories, e.g. baseline, current and history, add scanning-profile to results";
    reference "0.5.0";
  }

  revision "2019-04-11" {
    description
      "Add otdr repetition, dynamic-range, dead-zone, etc.,
      modify rpc response structure";
    reference "0.4.0";
  }

  revision "2019-04-01" {
    description
      "Revised version from Alibaba";
    reference "0.3.0";
  }

  revision "2019-03-29" {
    description
      "Initial version from Alibaba";
    reference "0.2.0";
  }

  revision "2018-08-28" {
    description
      "Initial revision";
    reference "0.1.0";
  }

  // typedef statements

  typedef otdr-event-type {
    type enumeration {
      enum START {
        description
          "Start-Event on a OTDR trace is the initial point";
      }
      enum END {
        description
          "End-Event on a OTDR trace is the end point of a fiber";
      }
      enum REFLECTION {
        description
          "The phenonmenon on a trace that some power of an optical
          pulse is reflected called a reflection event. It is displayed
          as a peak signal on a trace";
      }
      enum NON-REFLECTION {
        description
          "The phenonmenon on a trace that there exists some abnormal
          loss in an optical line, but no reflection occurred is called
          a Non-Reflection-Event. It is displayed as a drop with no peak";
      }
      enum FIBER-SECTION {
        description
        "A fiber section as an event";
      }
      enum UNKOWN {
        description
        "Unknown otdr event";
      }
    }
  }

  // grouping statements
  grouping otdr-fiber-profile {
    description
      "Enclosing container for otdr fiber-profile configuration";

    container fiber-profile {

      leaf refractive-index {
        type decimal64 {
          fraction-digits 4;
        }

        description
          "refractive ratio";
      }

      leaf backscatter-index {
        type decimal64 {
          fraction-digits 2;
        }

        description
          "backscatter ratio";
      }

      leaf reflection-threshold {
        type decimal64 {
          fraction-digits 2;
        }
        description
	  "reflection threshold";
      }

      leaf splice-loss-threshold {
        type decimal64 {
          fraction-digits 2;
        }

        description
          "splice loss threshold";
      }

      leaf end-of-fiber-threshold {
        type decimal64 {
          fraction-digits 2;
        }
        description
          "fiber end event threshold";
      }
    }
  }

  grouping otdr-scanning-profile {
    description
      "Enclosing container for otdr scanning profile configuration";

    container scanning-profile {

      leaf distance-range {
        type uint32;
        units km;
        description
          "distance range in km";
      }

      leaf pulse-width {
        type uint32;
        units ns;
        description
          "pulse width in ns";
      }

      leaf average-time {
        type uint32;
        units s;
        description
          "Average time of each scanning";
      }

      leaf output-frequency {
        type oc-opt-types:frequency-type;
        description
          "The output frequency in MHz of the OTDR";
      }
    }
  }

  grouping otdr-repetition {
    description
      "Enclosing container for otdr repetition configuration";

    container repetition {

      leaf enable {
        type boolean;
        description
          "Repetition or not. If True, then
          periodic scan the fiber with given frequency";
        default false;
      }

      leaf start-time {
        type oc-yang:date-and-time;
        description
          "The start date and time of the repetition";
      }

      leaf period {
        type uint32;
        units s;
        description
          "The scan period of the repetition, e.g. 60s, 15*60s, 24*60*60s";
      }
    }
  }


  grouping otdr-config {
    description
      "Configuration data for otdr scan definitions";

    leaf name {
      type leafref {
        path "/oc-platform:components/oc-platform:component/"
                 + "oc-platform:name";
        }
    description
      "OTDR name";
    }

    leaf parent-port {
      type leafref {
        path "/oc-platform:components/oc-platform:component/"
                 + "oc-platform:name";
      }
	description
	  "OTDR scan port";
    }

    uses otdr-fiber-profile;
    uses otdr-scanning-profile;
    uses otdr-repetition;
  }

  grouping otdr-specification {
    description
      "Enclosing container for otdr repetition configuration";

    container specification {

      leaf dynamic-range {
        type uint32;
        units dB;
        description
          "The dynamic range of the OTDR.";
      }

      leaf distance-accuracy {
        type decimal64 {
          fraction-digits 2;
        }

        units m;
        description
        "The distance accuracy of each event";
      }

      leaf sampling-resolution {
        type decimal64 {
          fraction-digits 2;
        }
        units m;
        description
        "sampling resolution of the otdr, with unit of meters";
      }

      leaf loss-dead-zone {
        type decimal64 {
          fraction-digits 2;
        }

        units m;
        description
        "The dead zone of loss event";
      }

      leaf reflection-dead-zone {
        type decimal64 {
          fraction-digits 2;
        }

        units m;
        description
        "The dead zone of reflection event";
      }
    }
  }

  grouping otdr-state {
    description
      "Operational state data for media channels ";

    uses otdr-specification;

    leaf scanning-status {
      type identityref {
        base oc-platform-types:COMPONENT_OPER_STATUS;
      }
      description
        "This reports the current scanning status
        of the OTDR.";
    }
  }

  grouping otdr-events {
    description
      "Top-level grouping for OTDR results";

    container events {
      description
        "Enclosing container for otdr results list";

      leaf scan-time {
        type oc-yang:date-and-time;
        description
          "Time of each scanning operation, including date and time";
      }

      leaf span-distance {
        type decimal64 {
          fraction-digits 2;
        }

        units km;
        description
        "Total length of a fiber span";
      }

      leaf span-loss {
        type decimal64 {
          fraction-digits 2;
        }

        units dB;
        description
        "Total loss of a fiber span";
      }

      list event {
        key index;
        description
          "List of otdr results";

        leaf index {
          type uint16;
          description
            "Index of event";
        }

        leaf type {
          type otdr-event-type;
          description
          "Event type";
        }

        leaf length {
          type decimal64 {
            fraction-digits 2;
          }

          units km;
          description
          "Event distance or fiber section length in km";
        }

        leaf loss {
          type decimal64 {
            fraction-digits 2;
          }

          description
          "Event loss in dB";
        }

        leaf reflection {
          type decimal64 {
            fraction-digits 2;
          }

          description
          "Event reflection in dB";
        }

        leaf accumulate-loss {
          type decimal64 {
            fraction-digits 2;
          }

          description
          "Accumulated loss at the event point";
        }
      }
    }
  }

  grouping otdr-result-trace {
    description
      "Top-level grouping for OTDR result waveform";

    container trace {

      leaf update-time {
        type oc-yang:date-and-time;
        description
          "Update time of the trace, including date and time";
      }

      leaf data {
        type oc-yang:hex-string;
      }

      description
      "Need to consider if there is a better way to collect the waveform";
    }
  }

  grouping otdr-result-top {
    description
      "Top-level grouping for OTDR result";

    uses otdr-scanning-profile;
    uses otdr-events;
    uses otdr-result-trace;
  }

  grouping otdr-results-top {
    description
      "Top-level grouping for OTDR result";

    list result {
      key scan-time;
      description
        "List of otdr results";

      leaf scan-time {
        type leafref {
          path "../events/scan-time";
        }
        description
          "Time of each scanning operation, including date and time";
      }

      uses otdr-result-top;
    }
  }

  grouping otdr-top {
    description
      "Top-level grouping for list of defined OTDR monitors";

    container otdrs {
      description
        "Enclosing container for OTDR scan list";

      list otdr {
        key name;
        description
          "List of OTDRs";

        leaf name {
          type leafref {
            path "../config/name";
          }
          description
            "Reference to name to be monitored";
        }

        container config {
          description
            "Configuration data";

          uses otdr-config;
        }

        container state {

          config false;

          description
            "Operational state data";

          uses otdr-config;
          uses otdr-state;
        }

        container baseline-result {

          config false;

          description
            "Enclosing container for otdr baseline results";

          uses otdr-result-top;
        }

        container current-result {

          config false;


          description
            "Enclosing container for otdr current results";

          uses otdr-result-top;
        }

        container history-results {

          config false;

          description
            "Enclosing container for otdr history results";

          uses otdr-results-top;
        }
      }
    }
  }

  // data definition statements

  uses otdr-top;

  // augment statements
  // rpc statements


  rpc trigger-a-shot {
    description
      "The RPC instantly trigger the otdr and send back the results, if the
       scanning-status of the otdr is active, the result is empty with informative
       message";

    input {
      leaf name {
        type leafref {
          path "/oc-otdr:otdrs/otdr/config/oc-otdr:name";
        }
      }
    }
    output {
      leaf message {
        type string;
        description
          "Informational response for the otdr results";
      }

      uses otdr-result-top;
    }
  }

  rpc load-results {
    description
      "The RPC select a section of time and ask to send back the all the results
       within the time section";

    input  {
      leaf name {
        type leafref {
          path "/oc-otdr:otdrs/otdr/config/oc-otdr:name";
        }
      }

      leaf start-time {
        type oc-yang:date-and-time;
        description
          "Start time for a period, including date and time";
      }

      leaf end-time {
        type oc-yang:date-and-time;
        description
          "End time for a period, including date and time";
      }
    }

    output  {
      leaf message {
        type string;
        description
          "Informational response for the otdr results";
      }

      uses otdr-results-top;
    }
  }

  rpc update-baseline {
    description
      "The RPC will update the baseline result according to the scan time";

    input  {
      leaf name {
        type leafref {
          path "/oc-otdr:otdrs/otdr/config/oc-otdr:name";
        }
      }

      leaf scan-time {
        type oc-yang:date-and-time;
        description
          "Update baseline-result, according to scan time";
      }
    }

    output  {
      leaf message {
        type string;
        description
          "Informational response for the otdr results";
      }

      uses otdr-result-top;
    }
  }

}
