module openconfig-system-annot {

    yang-version "";

    namespace "http://openconfig.net/yang/annotation/oc-sys-annot";
    prefix "oc-sys-annot";

    import openconfig-procmon { prefix oc-proc; }
    import openconfig-alarms { prefix oc-alarms; }
    import openconfig-inet-types { prefix oc-inet; }
    import openconfig-yang-types { prefix oc-yang; }
    import openconfig-extensions { prefix oc-ext; }
    import openconfig-aaa { prefix oc-aaa; }
    import openconfig-system-logging { prefix oc-log; }
    import openconfig-system-management { prefix oc-sys-mgmt; }
    import openconfig-types { prefix oc-types; }
    import openconfig-system-terminal { prefix oc-sys-term; }
    import openconfig-messages { prefix oc-messages; }
    import openconfig-system { prefix oc-sys; }

    deviation /oc-sys:system {
      deviate add {
        sonic-ext:table-name "SYSTEM";
      }
    }

    deviation /oc-sys:system/oc-sys:telnet-server {
      deviate add {
      }
    }

    deviation /oc-sys:system/oc-sys:telnet-server/oc-sys:config {
      deviate add {
      }
    }

    deviation /oc-sys:system/oc-sys:telnet-server/oc-sys:config/oc-sys:enable {
      deviate add {
      }
    }

    deviation /oc-sys:system/oc-sys:telnet-server/oc-sys:config/oc-sys:timeout {
      deviate add {
      }
    }

    deviation /oc-sys:system/oc-sys:telnet-server/oc-sys:config/oc-sys:rate-limit {
      deviate add {
      }
    }

    deviation /oc-sys:system/oc-sys:telnet-server/oc-sys:config/oc-sys:session-limit {
      deviate add {
      }
    }

    deviation /oc-sys:system/oc-sys:telnet-server/oc-sys:state {
      deviate add {
      }
    }

    deviation /oc-sys:system/oc-sys:telnet-server/oc-sys:state/oc-sys:rate-limit {
      deviate add {
      }
    }

    deviation /oc-sys:system/oc-sys:telnet-server/oc-sys:state/oc-sys:session-limit {
      deviate add {
      }
    }

    deviation /oc-sys:system/oc-sys:telnet-server/oc-sys:state/oc-sys:enable {
      deviate add {
      }
    }

    deviation /oc-sys:system/oc-sys:telnet-server/oc-sys:state/oc-sys:timeout {
      deviate add {
      }
    }

    deviation /oc-sys:system/oc-sys:ssh-server {
      deviate add {
      }
    }

    deviation /oc-sys:system/oc-sys:ssh-server/oc-sys:config {
      deviate add {
      }
    }

    deviation /oc-sys:system/oc-sys:ssh-server/oc-sys:config/oc-sys:timeout {
      deviate add {
      }
    }

    deviation /oc-sys:system/oc-sys:ssh-server/oc-sys:config/oc-sys:enable {
      deviate add {
      }
    }

    deviation /oc-sys:system/oc-sys:ssh-server/oc-sys:config/oc-sys:protocol-version {
      deviate add {
      }
    }

    deviation /oc-sys:system/oc-sys:ssh-server/oc-sys:config/oc-sys:rate-limit {
      deviate add {
      }
    }

    deviation /oc-sys:system/oc-sys:ssh-server/oc-sys:config/oc-sys:session-limit {
      deviate add {
      }
    }

    deviation /oc-sys:system/oc-sys:ssh-server/oc-sys:state {
      deviate add {
      }
    }

    deviation /oc-sys:system/oc-sys:ssh-server/oc-sys:state/oc-sys:session-limit {
      deviate add {
      }
    }

    deviation /oc-sys:system/oc-sys:ssh-server/oc-sys:state/oc-sys:timeout {
      deviate add {
      }
    }

    deviation /oc-sys:system/oc-sys:ssh-server/oc-sys:state/oc-sys:enable {
      deviate add {
      }
    }

    deviation /oc-sys:system/oc-sys:ssh-server/oc-sys:state/oc-sys:protocol-version {
      deviate add {
      }
    }

    deviation /oc-sys:system/oc-sys:ssh-server/oc-sys:state/oc-sys:rate-limit {
      deviate add {
      }
    }

    deviation /oc-sys:system/oc-sys:grpc-server {
      deviate add {
      }
    }

    deviation /oc-sys:system/oc-sys:grpc-server/oc-sys:config {
      deviate add {
      }
    }

    deviation /oc-sys:system/oc-sys:grpc-server/oc-sys:config/oc-sys:port {
      deviate add {
      }
    }

    deviation /oc-sys:system/oc-sys:grpc-server/oc-sys:config/oc-sys:transport-security {
      deviate add {
      }
    }

    deviation /oc-sys:system/oc-sys:grpc-server/oc-sys:config/oc-sys:certificate-id {
      deviate add {
      }
    }

    deviation /oc-sys:system/oc-sys:grpc-server/oc-sys:config/oc-sys:listen-addresses {
      deviate add {
      }
    }

    deviation /oc-sys:system/oc-sys:grpc-server/oc-sys:config/oc-sys:enable {
      deviate add {
      }
    }

    deviation /oc-sys:system/oc-sys:grpc-server/oc-sys:state {
      deviate add {
      }
    }

    deviation /oc-sys:system/oc-sys:grpc-server/oc-sys:state/oc-sys:certificate-id {
      deviate add {
      }
    }

    deviation /oc-sys:system/oc-sys:grpc-server/oc-sys:state/oc-sys:listen-addresses {
      deviate add {
      }
    }

    deviation /oc-sys:system/oc-sys:grpc-server/oc-sys:state/oc-sys:enable {
      deviate add {
      }
    }

    deviation /oc-sys:system/oc-sys:grpc-server/oc-sys:state/oc-sys:port {
      deviate add {
      }
    }

    deviation /oc-sys:system/oc-sys:grpc-server/oc-sys:state/oc-sys:transport-security {
      deviate add {
      }
    }

    deviation /oc-sys:system/oc-sys:state {
      deviate add {
      }
    }

    deviation /oc-sys:system/oc-sys:state/oc-sys:domain-name {
      deviate add {
      }
    }

    deviation /oc-sys:system/oc-sys:state/oc-sys:login-banner {
      deviate add {
      }
    }

    deviation /oc-sys:system/oc-sys:state/oc-sys:motd-banner {
      deviate add {
      }
    }

    deviation /oc-sys:system/oc-sys:state/oc-sys:current-datetime {
      deviate add {
      }
    }

    deviation /oc-sys:system/oc-sys:state/oc-sys:boot-time {
      deviate add {
      }
    }

    deviation /oc-sys:system/oc-sys:state/oc-sys:hostname {
      deviate add {
      }
    }

    deviation /oc-sys:system/oc-sys:clock {
      deviate add {
      }
    }

    deviation /oc-sys:system/oc-sys:clock/oc-sys:state {
      deviate add {
      }
    }

    deviation /oc-sys:system/oc-sys:clock/oc-sys:state/oc-sys:timezone-name {
      deviate add {
      }
    }

    deviation /oc-sys:system/oc-sys:clock/oc-sys:config {
      deviate add {
      }
    }

    deviation /oc-sys:system/oc-sys:clock/oc-sys:config/oc-sys:timezone-name {
      deviate add {
      }
    }

    deviation /oc-sys:system/oc-sys:memory {
      deviate add {
      }
    }

    deviation /oc-sys:system/oc-sys:memory/oc-sys:config {
      deviate add {
      }
    }

    deviation /oc-sys:system/oc-sys:memory/oc-sys:state {
      deviate add {
      }
    }

    deviation /oc-sys:system/oc-sys:memory/oc-sys:state/oc-sys:reserved {
      deviate add {
      }
    }

    deviation /oc-sys:system/oc-sys:memory/oc-sys:state/oc-sys:physical {
      deviate add {
      }
    }

    deviation /oc-sys:system/oc-sys:dns {
      deviate add {
      }
    }

    deviation /oc-sys:system/oc-sys:dns/oc-sys:state {
      deviate add {
      }
    }

    deviation /oc-sys:system/oc-sys:dns/oc-sys:state/oc-sys:search {
      deviate add {
      }
    }

    deviation /oc-sys:system/oc-sys:dns/oc-sys:servers {
      deviate add {
      }
    }

    deviation /oc-sys:system/oc-sys:dns/oc-sys:servers/oc-sys:server {
      deviate add {
      }
    }

    deviation /oc-sys:system/oc-sys:dns/oc-sys:servers/oc-sys:server/oc-sys:address {
      deviate add {
      }
    }

    deviation /oc-sys:system/oc-sys:dns/oc-sys:servers/oc-sys:server/oc-sys:config {
      deviate add {
      }
    }

    deviation /oc-sys:system/oc-sys:dns/oc-sys:servers/oc-sys:server/oc-sys:config/oc-sys:address {
      deviate add {
      }
    }

    deviation /oc-sys:system/oc-sys:dns/oc-sys:servers/oc-sys:server/oc-sys:config/oc-sys:port {
      deviate add {
      }
    }

    deviation /oc-sys:system/oc-sys:dns/oc-sys:servers/oc-sys:server/oc-sys:state {
      deviate add {
      }
    }

    deviation /oc-sys:system/oc-sys:dns/oc-sys:servers/oc-sys:server/oc-sys:state/oc-sys:port {
      deviate add {
      }
    }

    deviation /oc-sys:system/oc-sys:dns/oc-sys:servers/oc-sys:server/oc-sys:state/oc-sys:address {
      deviate add {
      }
    }

    deviation /oc-sys:system/oc-sys:dns/oc-sys:host-entries {
      deviate add {
      }
    }

    deviation /oc-sys:system/oc-sys:dns/oc-sys:host-entries/oc-sys:host-entry {
      deviate add {
      }
    }

    deviation /oc-sys:system/oc-sys:dns/oc-sys:host-entries/oc-sys:host-entry/oc-sys:config {
      deviate add {
      }
    }

    deviation /oc-sys:system/oc-sys:dns/oc-sys:host-entries/oc-sys:host-entry/oc-sys:config/oc-sys:hostname {
      deviate add {
      }
    }

    deviation /oc-sys:system/oc-sys:dns/oc-sys:host-entries/oc-sys:host-entry/oc-sys:config/oc-sys:alias {
      deviate add {
      }
    }

    deviation /oc-sys:system/oc-sys:dns/oc-sys:host-entries/oc-sys:host-entry/oc-sys:config/oc-sys:ipv4-address {
      deviate add {
      }
    }

    deviation /oc-sys:system/oc-sys:dns/oc-sys:host-entries/oc-sys:host-entry/oc-sys:config/oc-sys:ipv6-address {
      deviate add {
      }
    }

    deviation /oc-sys:system/oc-sys:dns/oc-sys:host-entries/oc-sys:host-entry/oc-sys:state {
      deviate add {
      }
    }

    deviation /oc-sys:system/oc-sys:dns/oc-sys:host-entries/oc-sys:host-entry/oc-sys:state/oc-sys:alias {
      deviate add {
      }
    }

    deviation /oc-sys:system/oc-sys:dns/oc-sys:host-entries/oc-sys:host-entry/oc-sys:state/oc-sys:ipv4-address {
      deviate add {
      }
    }

    deviation /oc-sys:system/oc-sys:dns/oc-sys:host-entries/oc-sys:host-entry/oc-sys:state/oc-sys:ipv6-address {
      deviate add {
      }
    }

    deviation /oc-sys:system/oc-sys:dns/oc-sys:host-entries/oc-sys:host-entry/oc-sys:state/oc-sys:hostname {
      deviate add {
      }
    }

    deviation /oc-sys:system/oc-sys:dns/oc-sys:host-entries/oc-sys:host-entry/oc-sys:hostname {
      deviate add {
      }
    }

    deviation /oc-sys:system/oc-sys:dns/oc-sys:config {
      deviate add {
      }
    }

    deviation /oc-sys:system/oc-sys:dns/oc-sys:config/oc-sys:search {
      deviate add {
      }
    }

    deviation /oc-sys:system/oc-sys:ntp {
      deviate add {
      }
    }

    deviation /oc-sys:system/oc-sys:ntp/oc-sys:config {
      deviate add {
      }
    }

    deviation /oc-sys:system/oc-sys:ntp/oc-sys:config/oc-sys:ntp-source-address {
      deviate add {
      }
    }

    deviation /oc-sys:system/oc-sys:ntp/oc-sys:config/oc-sys:enable-ntp-auth {
      deviate add {
      }
    }

    deviation /oc-sys:system/oc-sys:ntp/oc-sys:config/oc-sys:enabled {
      deviate add {
      }
    }

    deviation /oc-sys:system/oc-sys:ntp/oc-sys:state {
      deviate add {
      }
    }

    deviation /oc-sys:system/oc-sys:ntp/oc-sys:state/oc-sys:enabled {
      deviate add {
      }
    }

    deviation /oc-sys:system/oc-sys:ntp/oc-sys:state/oc-sys:ntp-source-address {
      deviate add {
      }
    }

    deviation /oc-sys:system/oc-sys:ntp/oc-sys:state/oc-sys:auth-mismatch {
      deviate add {
      }
    }

    deviation /oc-sys:system/oc-sys:ntp/oc-sys:state/oc-sys:enable-ntp-auth {
      deviate add {
      }
    }

    deviation /oc-sys:system/oc-sys:ntp/oc-sys:ntp-keys {
      deviate add {
      }
    }

    deviation /oc-sys:system/oc-sys:ntp/oc-sys:ntp-keys/oc-sys:ntp-key {
      deviate add {
      }
    }

    deviation /oc-sys:system/oc-sys:ntp/oc-sys:ntp-keys/oc-sys:ntp-key/oc-sys:key-id {
      deviate add {
      }
    }

    deviation /oc-sys:system/oc-sys:ntp/oc-sys:ntp-keys/oc-sys:ntp-key/oc-sys:config {
      deviate add {
      }
    }

    deviation /oc-sys:system/oc-sys:ntp/oc-sys:ntp-keys/oc-sys:ntp-key/oc-sys:config/oc-sys:key-value {
      deviate add {
      }
    }

    deviation /oc-sys:system/oc-sys:ntp/oc-sys:ntp-keys/oc-sys:ntp-key/oc-sys:config/oc-sys:key-id {
      deviate add {
      }
    }

    deviation /oc-sys:system/oc-sys:ntp/oc-sys:ntp-keys/oc-sys:ntp-key/oc-sys:config/oc-sys:key-type {
      deviate add {
      }
    }

    deviation /oc-sys:system/oc-sys:ntp/oc-sys:ntp-keys/oc-sys:ntp-key/oc-sys:state {
      deviate add {
      }
    }

    deviation /oc-sys:system/oc-sys:ntp/oc-sys:ntp-keys/oc-sys:ntp-key/oc-sys:state/oc-sys:key-type {
      deviate add {
      }
    }

    deviation /oc-sys:system/oc-sys:ntp/oc-sys:ntp-keys/oc-sys:ntp-key/oc-sys:state/oc-sys:key-value {
      deviate add {
      }
    }

    deviation /oc-sys:system/oc-sys:ntp/oc-sys:ntp-keys/oc-sys:ntp-key/oc-sys:state/oc-sys:key-id {
      deviate add {
      }
    }

    deviation /oc-sys:system/oc-sys:ntp/oc-sys:servers {
      deviate add {
      }
    }

    deviation /oc-sys:system/oc-sys:ntp/oc-sys:servers/oc-sys:server {
      deviate add {
      }
    }

    deviation /oc-sys:system/oc-sys:ntp/oc-sys:servers/oc-sys:server/oc-sys:address {
      deviate add {
      }
    }

    deviation /oc-sys:system/oc-sys:ntp/oc-sys:servers/oc-sys:server/oc-sys:config {
      deviate add {
      }
    }

    deviation /oc-sys:system/oc-sys:ntp/oc-sys:servers/oc-sys:server/oc-sys:config/oc-sys:address {
      deviate add {
      }
    }

    deviation /oc-sys:system/oc-sys:ntp/oc-sys:servers/oc-sys:server/oc-sys:config/oc-sys:port {
      deviate add {
      }
    }

    deviation /oc-sys:system/oc-sys:ntp/oc-sys:servers/oc-sys:server/oc-sys:config/oc-sys:version {
      deviate add {
      }
    }

    deviation /oc-sys:system/oc-sys:ntp/oc-sys:servers/oc-sys:server/oc-sys:config/oc-sys:association-type {
      deviate add {
      }
    }

    deviation /oc-sys:system/oc-sys:ntp/oc-sys:servers/oc-sys:server/oc-sys:config/oc-sys:iburst {
      deviate add {
      }
    }

    deviation /oc-sys:system/oc-sys:ntp/oc-sys:servers/oc-sys:server/oc-sys:config/oc-sys:prefer {
      deviate add {
      }
    }

    deviation /oc-sys:system/oc-sys:ntp/oc-sys:servers/oc-sys:server/oc-sys:state {
      deviate add {
      }
    }

    deviation /oc-sys:system/oc-sys:ntp/oc-sys:servers/oc-sys:server/oc-sys:state/oc-sys:iburst {
      deviate add {
      }
    }

    deviation /oc-sys:system/oc-sys:ntp/oc-sys:servers/oc-sys:server/oc-sys:state/oc-sys:association-type {
      deviate add {
      }
    }

    deviation /oc-sys:system/oc-sys:ntp/oc-sys:servers/oc-sys:server/oc-sys:state/oc-sys:address {
      deviate add {
      }
    }

    deviation /oc-sys:system/oc-sys:ntp/oc-sys:servers/oc-sys:server/oc-sys:state/oc-sys:poll-interval {
      deviate add {
      }
    }

    deviation /oc-sys:system/oc-sys:ntp/oc-sys:servers/oc-sys:server/oc-sys:state/oc-sys:prefer {
      deviate add {
      }
    }

    deviation /oc-sys:system/oc-sys:ntp/oc-sys:servers/oc-sys:server/oc-sys:state/oc-sys:offset {
      deviate add {
      }
    }

    deviation /oc-sys:system/oc-sys:ntp/oc-sys:servers/oc-sys:server/oc-sys:state/oc-sys:root-delay {
      deviate add {
      }
    }

    deviation /oc-sys:system/oc-sys:ntp/oc-sys:servers/oc-sys:server/oc-sys:state/oc-sys:stratum {
      deviate add {
      }
    }

    deviation /oc-sys:system/oc-sys:ntp/oc-sys:servers/oc-sys:server/oc-sys:state/oc-sys:version {
      deviate add {
      }
    }

    deviation /oc-sys:system/oc-sys:ntp/oc-sys:servers/oc-sys:server/oc-sys:state/oc-sys:root-dispersion {
      deviate add {
      }
    }

    deviation /oc-sys:system/oc-sys:ntp/oc-sys:servers/oc-sys:server/oc-sys:state/oc-sys:port {
      deviate add {
      }
    }

    deviation /oc-sys:system/oc-sys:config {
      deviate add {
      }
    }

    deviation /oc-sys:system/oc-sys:config/oc-sys:motd-banner {
      deviate add {
      }
    }

    deviation /oc-sys:system/oc-sys:config/oc-sys:hostname {
      deviate add {
        sonic-ext:field-name "hostname";
      }
    }

    deviation /oc-sys:system/oc-sys:config/oc-sys:domain-name {
      deviate add {
      }
    }

    deviation /oc-sys:system/oc-sys:config/oc-sys:login-banner {
      deviate add {
      }
    }

    deviation /oc-sys:system/oc-sys:cpus {
      deviate add {
      }
    }

    deviation /oc-sys:system/oc-sys:cpus/oc-sys:cpu {
      deviate add {
      }
    }

    deviation /oc-sys:system/oc-sys:cpus/oc-sys:cpu/oc-sys:state {
      deviate add {
      }
    }

    deviation /oc-sys:system/oc-sys:cpus/oc-sys:cpu/oc-sys:state/oc-sys:hardware-interrupt {
      deviate add {
      }
    }

    deviation /oc-sys:system/oc-sys:cpus/oc-sys:cpu/oc-sys:state/oc-sys:hardware-interrupt/oc-sys:min-time {
      deviate add {
      }
    }

    deviation /oc-sys:system/oc-sys:cpus/oc-sys:cpu/oc-sys:state/oc-sys:hardware-interrupt/oc-sys:max-time {
      deviate add {
      }
    }

    deviation /oc-sys:system/oc-sys:cpus/oc-sys:cpu/oc-sys:state/oc-sys:hardware-interrupt/oc-sys:instant {
      deviate add {
      }
    }

    deviation /oc-sys:system/oc-sys:cpus/oc-sys:cpu/oc-sys:state/oc-sys:hardware-interrupt/oc-sys:avg {
      deviate add {
      }
    }

    deviation /oc-sys:system/oc-sys:cpus/oc-sys:cpu/oc-sys:state/oc-sys:hardware-interrupt/oc-sys:min {
      deviate add {
      }
    }

    deviation /oc-sys:system/oc-sys:cpus/oc-sys:cpu/oc-sys:state/oc-sys:hardware-interrupt/oc-sys:max {
      deviate add {
      }
    }

    deviation /oc-sys:system/oc-sys:cpus/oc-sys:cpu/oc-sys:state/oc-sys:hardware-interrupt/oc-sys:interval {
      deviate add {
      }
    }

    deviation /oc-sys:system/oc-sys:cpus/oc-sys:cpu/oc-sys:state/oc-sys:user {
      deviate add {
      }
    }

    deviation /oc-sys:system/oc-sys:cpus/oc-sys:cpu/oc-sys:state/oc-sys:user/oc-sys:interval {
      deviate add {
      }
    }

    deviation /oc-sys:system/oc-sys:cpus/oc-sys:cpu/oc-sys:state/oc-sys:user/oc-sys:min-time {
      deviate add {
      }
    }

    deviation /oc-sys:system/oc-sys:cpus/oc-sys:cpu/oc-sys:state/oc-sys:user/oc-sys:max-time {
      deviate add {
      }
    }

    deviation /oc-sys:system/oc-sys:cpus/oc-sys:cpu/oc-sys:state/oc-sys:user/oc-sys:instant {
      deviate add {
      }
    }

    deviation /oc-sys:system/oc-sys:cpus/oc-sys:cpu/oc-sys:state/oc-sys:user/oc-sys:avg {
      deviate add {
      }
    }

    deviation /oc-sys:system/oc-sys:cpus/oc-sys:cpu/oc-sys:state/oc-sys:user/oc-sys:min {
      deviate add {
      }
    }

    deviation /oc-sys:system/oc-sys:cpus/oc-sys:cpu/oc-sys:state/oc-sys:user/oc-sys:max {
      deviate add {
      }
    }

    deviation /oc-sys:system/oc-sys:cpus/oc-sys:cpu/oc-sys:state/oc-sys:kernel {
      deviate add {
      }
    }

    deviation /oc-sys:system/oc-sys:cpus/oc-sys:cpu/oc-sys:state/oc-sys:kernel/oc-sys:max-time {
      deviate add {
      }
    }

    deviation /oc-sys:system/oc-sys:cpus/oc-sys:cpu/oc-sys:state/oc-sys:kernel/oc-sys:instant {
      deviate add {
      }
    }

    deviation /oc-sys:system/oc-sys:cpus/oc-sys:cpu/oc-sys:state/oc-sys:kernel/oc-sys:avg {
      deviate add {
      }
    }

    deviation /oc-sys:system/oc-sys:cpus/oc-sys:cpu/oc-sys:state/oc-sys:kernel/oc-sys:min {
      deviate add {
      }
    }

    deviation /oc-sys:system/oc-sys:cpus/oc-sys:cpu/oc-sys:state/oc-sys:kernel/oc-sys:max {
      deviate add {
      }
    }

    deviation /oc-sys:system/oc-sys:cpus/oc-sys:cpu/oc-sys:state/oc-sys:kernel/oc-sys:interval {
      deviate add {
      }
    }

    deviation /oc-sys:system/oc-sys:cpus/oc-sys:cpu/oc-sys:state/oc-sys:kernel/oc-sys:min-time {
      deviate add {
      }
    }

    deviation /oc-sys:system/oc-sys:cpus/oc-sys:cpu/oc-sys:state/oc-sys:idle {
      deviate add {
      }
    }

    deviation /oc-sys:system/oc-sys:cpus/oc-sys:cpu/oc-sys:state/oc-sys:idle/oc-sys:min {
      deviate add {
      }
    }

    deviation /oc-sys:system/oc-sys:cpus/oc-sys:cpu/oc-sys:state/oc-sys:idle/oc-sys:max {
      deviate add {
      }
    }

    deviation /oc-sys:system/oc-sys:cpus/oc-sys:cpu/oc-sys:state/oc-sys:idle/oc-sys:interval {
      deviate add {
      }
    }

    deviation /oc-sys:system/oc-sys:cpus/oc-sys:cpu/oc-sys:state/oc-sys:idle/oc-sys:min-time {
      deviate add {
      }
    }

    deviation /oc-sys:system/oc-sys:cpus/oc-sys:cpu/oc-sys:state/oc-sys:idle/oc-sys:max-time {
      deviate add {
      }
    }

    deviation /oc-sys:system/oc-sys:cpus/oc-sys:cpu/oc-sys:state/oc-sys:idle/oc-sys:instant {
      deviate add {
      }
    }

    deviation /oc-sys:system/oc-sys:cpus/oc-sys:cpu/oc-sys:state/oc-sys:idle/oc-sys:avg {
      deviate add {
      }
    }

    deviation /oc-sys:system/oc-sys:cpus/oc-sys:cpu/oc-sys:state/oc-sys:software-interrupt {
      deviate add {
      }
    }

    deviation /oc-sys:system/oc-sys:cpus/oc-sys:cpu/oc-sys:state/oc-sys:software-interrupt/oc-sys:avg {
      deviate add {
      }
    }

    deviation /oc-sys:system/oc-sys:cpus/oc-sys:cpu/oc-sys:state/oc-sys:software-interrupt/oc-sys:min {
      deviate add {
      }
    }

    deviation /oc-sys:system/oc-sys:cpus/oc-sys:cpu/oc-sys:state/oc-sys:software-interrupt/oc-sys:max {
      deviate add {
      }
    }

    deviation /oc-sys:system/oc-sys:cpus/oc-sys:cpu/oc-sys:state/oc-sys:software-interrupt/oc-sys:interval {
      deviate add {
      }
    }

    deviation /oc-sys:system/oc-sys:cpus/oc-sys:cpu/oc-sys:state/oc-sys:software-interrupt/oc-sys:min-time {
      deviate add {
      }
    }

    deviation /oc-sys:system/oc-sys:cpus/oc-sys:cpu/oc-sys:state/oc-sys:software-interrupt/oc-sys:max-time {
      deviate add {
      }
    }

    deviation /oc-sys:system/oc-sys:cpus/oc-sys:cpu/oc-sys:state/oc-sys:software-interrupt/oc-sys:instant {
      deviate add {
      }
    }

    deviation /oc-sys:system/oc-sys:cpus/oc-sys:cpu/oc-sys:state/oc-sys:nice {
      deviate add {
      }
    }

    deviation /oc-sys:system/oc-sys:cpus/oc-sys:cpu/oc-sys:state/oc-sys:nice/oc-sys:min-time {
      deviate add {
      }
    }

    deviation /oc-sys:system/oc-sys:cpus/oc-sys:cpu/oc-sys:state/oc-sys:nice/oc-sys:max-time {
      deviate add {
      }
    }

    deviation /oc-sys:system/oc-sys:cpus/oc-sys:cpu/oc-sys:state/oc-sys:nice/oc-sys:instant {
      deviate add {
      }
    }

    deviation /oc-sys:system/oc-sys:cpus/oc-sys:cpu/oc-sys:state/oc-sys:nice/oc-sys:avg {
      deviate add {
      }
    }

    deviation /oc-sys:system/oc-sys:cpus/oc-sys:cpu/oc-sys:state/oc-sys:nice/oc-sys:min {
      deviate add {
      }
    }

    deviation /oc-sys:system/oc-sys:cpus/oc-sys:cpu/oc-sys:state/oc-sys:nice/oc-sys:max {
      deviate add {
      }
    }

    deviation /oc-sys:system/oc-sys:cpus/oc-sys:cpu/oc-sys:state/oc-sys:nice/oc-sys:interval {
      deviate add {
      }
    }

    deviation /oc-sys:system/oc-sys:cpus/oc-sys:cpu/oc-sys:state/oc-sys:index {
      deviate add {
      }
    }

    deviation /oc-sys:system/oc-sys:cpus/oc-sys:cpu/oc-sys:state/oc-sys:total {
      deviate add {
      }
    }

    deviation /oc-sys:system/oc-sys:cpus/oc-sys:cpu/oc-sys:state/oc-sys:total/oc-sys:instant {
      deviate add {
      }
    }

    deviation /oc-sys:system/oc-sys:cpus/oc-sys:cpu/oc-sys:state/oc-sys:total/oc-sys:avg {
      deviate add {
      }
    }

    deviation /oc-sys:system/oc-sys:cpus/oc-sys:cpu/oc-sys:state/oc-sys:total/oc-sys:min {
      deviate add {
      }
    }

    deviation /oc-sys:system/oc-sys:cpus/oc-sys:cpu/oc-sys:state/oc-sys:total/oc-sys:max {
      deviate add {
      }
    }

    deviation /oc-sys:system/oc-sys:cpus/oc-sys:cpu/oc-sys:state/oc-sys:total/oc-sys:interval {
      deviate add {
      }
    }

    deviation /oc-sys:system/oc-sys:cpus/oc-sys:cpu/oc-sys:state/oc-sys:total/oc-sys:min-time {
      deviate add {
      }
    }

    deviation /oc-sys:system/oc-sys:cpus/oc-sys:cpu/oc-sys:state/oc-sys:total/oc-sys:max-time {
      deviate add {
      }
    }

    deviation /oc-sys:system/oc-sys:cpus/oc-sys:cpu/oc-sys:state/oc-sys:wait {
      deviate add {
      }
    }

    deviation /oc-sys:system/oc-sys:cpus/oc-sys:cpu/oc-sys:state/oc-sys:wait/oc-sys:min {
      deviate add {
      }
    }

    deviation /oc-sys:system/oc-sys:cpus/oc-sys:cpu/oc-sys:state/oc-sys:wait/oc-sys:max {
      deviate add {
      }
    }

    deviation /oc-sys:system/oc-sys:cpus/oc-sys:cpu/oc-sys:state/oc-sys:wait/oc-sys:interval {
      deviate add {
      }
    }

    deviation /oc-sys:system/oc-sys:cpus/oc-sys:cpu/oc-sys:state/oc-sys:wait/oc-sys:min-time {
      deviate add {
      }
    }

    deviation /oc-sys:system/oc-sys:cpus/oc-sys:cpu/oc-sys:state/oc-sys:wait/oc-sys:max-time {
      deviate add {
      }
    }

    deviation /oc-sys:system/oc-sys:cpus/oc-sys:cpu/oc-sys:state/oc-sys:wait/oc-sys:instant {
      deviate add {
      }
    }

    deviation /oc-sys:system/oc-sys:cpus/oc-sys:cpu/oc-sys:state/oc-sys:wait/oc-sys:avg {
      deviate add {
      }
    }

    deviation /oc-sys:system/oc-sys:cpus/oc-sys:cpu/oc-sys:index {
      deviate add {
      }
    }

    deviation /oc-sys:system/oc-sys:alarms {
      deviate add {
        sonic-ext:db-name "STATE_DB";
        sonic-ext:table-name "CURALARM_TABLE";
        sonic-ext:get-namespace "oc_sys_get_namespace_xfmr";
      }
    }

    deviation /oc-sys:system/oc-sys:alarms/oc-sys:alarm {
      deviate add {
        sonic-ext:key-transformer "oc_system_alarm_key_xfmr";
      }
    }

    deviation /oc-sys:system/oc-sys:alarms/oc-sys:alarm/oc-sys:id {
      deviate add {
      }
    }

    deviation /oc-sys:system/oc-sys:alarms/oc-sys:alarm/oc-sys:config {
      deviate add {
      }
    }

    deviation /oc-sys:system/oc-sys:alarms/oc-sys:alarm/oc-sys:state {
      deviate add {
        sonic-ext:db-name "STATE_DB";
        sonic-ext:table-name "CURALARM_TABLE";
        sonic-ext:key-transformer "oc_system_alarm_key_xfmr";
        sonic-ext:get-namespace "oc_sys_get_namespace_xfmr";
      }
    }

    deviation /oc-sys:system/oc-sys:alarms/oc-sys:alarm/oc-sys:state/oc-sys:type-id {
      deviate add {
        sonic-ext:field-name "type-id";
      }
    }

    deviation /oc-sys:system/oc-sys:alarms/oc-sys:alarm/oc-sys:state/oc-sys:id {
      deviate add {
      }
    }

    deviation /oc-sys:system/oc-sys:alarms/oc-sys:alarm/oc-sys:state/oc-sys:resource {
      deviate add {
        sonic-ext:field-name "resource";
      }
    }

    deviation /oc-sys:system/oc-sys:alarms/oc-sys:alarm/oc-sys:state/oc-sys:text {
      deviate add {
        sonic-ext:field-name "text";
      }
    }

    deviation /oc-sys:system/oc-sys:alarms/oc-sys:alarm/oc-sys:state/oc-sys:time-created {
      deviate add {
        sonic-ext:field-name "time-created";
      }
    }

    deviation /oc-sys:system/oc-sys:alarms/oc-sys:alarm/oc-sys:state/oc-sys:severity {
      deviate add {
        sonic-ext:field-name "severity";
      }
    }

    deviation /oc-sys:system/oc-sys:processes {
      deviate add {
      }
    }

    deviation /oc-sys:system/oc-sys:processes/oc-sys:process {
      deviate add {
      }
    }

    deviation /oc-sys:system/oc-sys:processes/oc-sys:process/oc-sys:pid {
      deviate add {
      }
    }

    deviation /oc-sys:system/oc-sys:processes/oc-sys:process/oc-sys:state {
      deviate add {
      }
    }

    deviation /oc-sys:system/oc-sys:processes/oc-sys:process/oc-sys:state/oc-sys:cpu-usage-user {
      deviate add {
      }
    }

    deviation /oc-sys:system/oc-sys:processes/oc-sys:process/oc-sys:state/oc-sys:cpu-utilization {
      deviate add {
      }
    }

    deviation /oc-sys:system/oc-sys:processes/oc-sys:process/oc-sys:state/oc-sys:name {
      deviate add {
      }
    }

    deviation /oc-sys:system/oc-sys:processes/oc-sys:process/oc-sys:state/oc-sys:memory-utilization {
      deviate add {
      }
    }

    deviation /oc-sys:system/oc-sys:processes/oc-sys:process/oc-sys:state/oc-sys:memory-usage {
      deviate add {
      }
    }

    deviation /oc-sys:system/oc-sys:processes/oc-sys:process/oc-sys:state/oc-sys:start-time {
      deviate add {
      }
    }

    deviation /oc-sys:system/oc-sys:processes/oc-sys:process/oc-sys:state/oc-sys:cpu-usage-system {
      deviate add {
      }
    }

    deviation /oc-sys:system/oc-sys:processes/oc-sys:process/oc-sys:state/oc-sys:args {
      deviate add {
      }
    }

    deviation /oc-sys:system/oc-sys:processes/oc-sys:process/oc-sys:state/oc-sys:pid {
      deviate add {
      }
    }

    deviation /oc-sys:system/oc-sys:processes/oc-sys:process/oc-sys:state/oc-sys:uptime {
      deviate add {
      }
    }

    deviation /oc-sys:system/oc-sys:aaa {
      deviate add {
      }
    }

    deviation /oc-sys:system/oc-sys:aaa/oc-sys:accounting {
      deviate add {
      }
    }

    deviation /oc-sys:system/oc-sys:aaa/oc-sys:accounting/oc-sys:config {
      deviate add {
      }
    }

    deviation /oc-sys:system/oc-sys:aaa/oc-sys:accounting/oc-sys:config/oc-sys:accounting-method {
      deviate add {
      }
    }

    deviation /oc-sys:system/oc-sys:aaa/oc-sys:accounting/oc-sys:state {
      deviate add {
      }
    }

    deviation /oc-sys:system/oc-sys:aaa/oc-sys:accounting/oc-sys:state/oc-sys:accounting-method {
      deviate add {
      }
    }

    deviation /oc-sys:system/oc-sys:aaa/oc-sys:accounting/oc-sys:events {
      deviate add {
      }
    }

    deviation /oc-sys:system/oc-sys:aaa/oc-sys:accounting/oc-sys:events/oc-sys:event {
      deviate add {
      }
    }

    deviation /oc-sys:system/oc-sys:aaa/oc-sys:accounting/oc-sys:events/oc-sys:event/oc-sys:event-type {
      deviate add {
      }
    }

    deviation /oc-sys:system/oc-sys:aaa/oc-sys:accounting/oc-sys:events/oc-sys:event/oc-sys:config {
      deviate add {
      }
    }

    deviation /oc-sys:system/oc-sys:aaa/oc-sys:accounting/oc-sys:events/oc-sys:event/oc-sys:config/oc-sys:event-type {
      deviate add {
      }
    }

    deviation /oc-sys:system/oc-sys:aaa/oc-sys:accounting/oc-sys:events/oc-sys:event/oc-sys:config/oc-sys:record {
      deviate add {
      }
    }

    deviation /oc-sys:system/oc-sys:aaa/oc-sys:accounting/oc-sys:events/oc-sys:event/oc-sys:state {
      deviate add {
      }
    }

    deviation /oc-sys:system/oc-sys:aaa/oc-sys:accounting/oc-sys:events/oc-sys:event/oc-sys:state/oc-sys:event-type {
      deviate add {
      }
    }

    deviation /oc-sys:system/oc-sys:aaa/oc-sys:accounting/oc-sys:events/oc-sys:event/oc-sys:state/oc-sys:record {
      deviate add {
      }
    }

    deviation /oc-sys:system/oc-sys:aaa/oc-sys:server-groups {
      deviate add {
      }
    }

    deviation /oc-sys:system/oc-sys:aaa/oc-sys:server-groups/oc-sys:server-group {
      deviate add {
      }
    }

    deviation /oc-sys:system/oc-sys:aaa/oc-sys:server-groups/oc-sys:server-group/oc-sys:servers {
      deviate add {
      }
    }

    deviation /oc-sys:system/oc-sys:aaa/oc-sys:server-groups/oc-sys:server-group/oc-sys:servers/oc-sys:server {
      deviate add {
      }
    }

    deviation /oc-sys:system/oc-sys:aaa/oc-sys:server-groups/oc-sys:server-group/oc-sys:servers/oc-sys:server/oc-sys:tacacs {
      deviate add {
      }
    }

    deviation /oc-sys:system/oc-sys:aaa/oc-sys:server-groups/oc-sys:server-group/oc-sys:servers/oc-sys:server/oc-sys:tacacs/oc-sys:state {
      deviate add {
      }
    }

    deviation /oc-sys:system/oc-sys:aaa/oc-sys:server-groups/oc-sys:server-group/oc-sys:servers/oc-sys:server/oc-sys:tacacs/oc-sys:state/oc-sys:source-address {
      deviate add {
      }
    }

    deviation /oc-sys:system/oc-sys:aaa/oc-sys:server-groups/oc-sys:server-group/oc-sys:servers/oc-sys:server/oc-sys:tacacs/oc-sys:state/oc-sys:port {
      deviate add {
      }
    }

    deviation /oc-sys:system/oc-sys:aaa/oc-sys:server-groups/oc-sys:server-group/oc-sys:servers/oc-sys:server/oc-sys:tacacs/oc-sys:state/oc-sys:secret-key {
      deviate add {
      }
    }

    deviation /oc-sys:system/oc-sys:aaa/oc-sys:server-groups/oc-sys:server-group/oc-sys:servers/oc-sys:server/oc-sys:tacacs/oc-sys:config {
      deviate add {
      }
    }

    deviation /oc-sys:system/oc-sys:aaa/oc-sys:server-groups/oc-sys:server-group/oc-sys:servers/oc-sys:server/oc-sys:tacacs/oc-sys:config/oc-sys:source-address {
      deviate add {
      }
    }

    deviation /oc-sys:system/oc-sys:aaa/oc-sys:server-groups/oc-sys:server-group/oc-sys:servers/oc-sys:server/oc-sys:tacacs/oc-sys:config/oc-sys:port {
      deviate add {
      }
    }

    deviation /oc-sys:system/oc-sys:aaa/oc-sys:server-groups/oc-sys:server-group/oc-sys:servers/oc-sys:server/oc-sys:tacacs/oc-sys:config/oc-sys:secret-key {
      deviate add {
      }
    }

    deviation /oc-sys:system/oc-sys:aaa/oc-sys:server-groups/oc-sys:server-group/oc-sys:servers/oc-sys:server/oc-sys:radius {
      deviate add {
      }
    }

    deviation /oc-sys:system/oc-sys:aaa/oc-sys:server-groups/oc-sys:server-group/oc-sys:servers/oc-sys:server/oc-sys:radius/oc-sys:state {
      deviate add {
      }
    }

    deviation /oc-sys:system/oc-sys:aaa/oc-sys:server-groups/oc-sys:server-group/oc-sys:servers/oc-sys:server/oc-sys:radius/oc-sys:state/oc-sys:source-address {
      deviate add {
      }
    }

    deviation /oc-sys:system/oc-sys:aaa/oc-sys:server-groups/oc-sys:server-group/oc-sys:servers/oc-sys:server/oc-sys:radius/oc-sys:state/oc-sys:retransmit-attempts {
      deviate add {
      }
    }

    deviation /oc-sys:system/oc-sys:aaa/oc-sys:server-groups/oc-sys:server-group/oc-sys:servers/oc-sys:server/oc-sys:radius/oc-sys:state/oc-sys:auth-port {
      deviate add {
      }
    }

    deviation /oc-sys:system/oc-sys:aaa/oc-sys:server-groups/oc-sys:server-group/oc-sys:servers/oc-sys:server/oc-sys:radius/oc-sys:state/oc-sys:acct-port {
      deviate add {
      }
    }

    deviation /oc-sys:system/oc-sys:aaa/oc-sys:server-groups/oc-sys:server-group/oc-sys:servers/oc-sys:server/oc-sys:radius/oc-sys:state/oc-sys:counters {
      deviate add {
      }
    }

    deviation /oc-sys:system/oc-sys:aaa/oc-sys:server-groups/oc-sys:server-group/oc-sys:servers/oc-sys:server/oc-sys:radius/oc-sys:state/oc-sys:counters/oc-sys:retried-access-requests {
      deviate add {
      }
    }

    deviation /oc-sys:system/oc-sys:aaa/oc-sys:server-groups/oc-sys:server-group/oc-sys:servers/oc-sys:server/oc-sys:radius/oc-sys:state/oc-sys:counters/oc-sys:access-accepts {
      deviate add {
      }
    }

    deviation /oc-sys:system/oc-sys:aaa/oc-sys:server-groups/oc-sys:server-group/oc-sys:servers/oc-sys:server/oc-sys:radius/oc-sys:state/oc-sys:counters/oc-sys:access-rejects {
      deviate add {
      }
    }

    deviation /oc-sys:system/oc-sys:aaa/oc-sys:server-groups/oc-sys:server-group/oc-sys:servers/oc-sys:server/oc-sys:radius/oc-sys:state/oc-sys:counters/oc-sys:timeout-access-requests {
      deviate add {
      }
    }

    deviation /oc-sys:system/oc-sys:aaa/oc-sys:server-groups/oc-sys:server-group/oc-sys:servers/oc-sys:server/oc-sys:radius/oc-sys:state/oc-sys:secret-key {
      deviate add {
      }
    }

    deviation /oc-sys:system/oc-sys:aaa/oc-sys:server-groups/oc-sys:server-group/oc-sys:servers/oc-sys:server/oc-sys:radius/oc-sys:config {
      deviate add {
      }
    }

    deviation /oc-sys:system/oc-sys:aaa/oc-sys:server-groups/oc-sys:server-group/oc-sys:servers/oc-sys:server/oc-sys:radius/oc-sys:config/oc-sys:auth-port {
      deviate add {
      }
    }

    deviation /oc-sys:system/oc-sys:aaa/oc-sys:server-groups/oc-sys:server-group/oc-sys:servers/oc-sys:server/oc-sys:radius/oc-sys:config/oc-sys:acct-port {
      deviate add {
      }
    }

    deviation /oc-sys:system/oc-sys:aaa/oc-sys:server-groups/oc-sys:server-group/oc-sys:servers/oc-sys:server/oc-sys:radius/oc-sys:config/oc-sys:secret-key {
      deviate add {
      }
    }

    deviation /oc-sys:system/oc-sys:aaa/oc-sys:server-groups/oc-sys:server-group/oc-sys:servers/oc-sys:server/oc-sys:radius/oc-sys:config/oc-sys:source-address {
      deviate add {
      }
    }

    deviation /oc-sys:system/oc-sys:aaa/oc-sys:server-groups/oc-sys:server-group/oc-sys:servers/oc-sys:server/oc-sys:radius/oc-sys:config/oc-sys:retransmit-attempts {
      deviate add {
      }
    }

    deviation /oc-sys:system/oc-sys:aaa/oc-sys:server-groups/oc-sys:server-group/oc-sys:servers/oc-sys:server/oc-sys:address {
      deviate add {
      }
    }

    deviation /oc-sys:system/oc-sys:aaa/oc-sys:server-groups/oc-sys:server-group/oc-sys:servers/oc-sys:server/oc-sys:config {
      deviate add {
      }
    }

    deviation /oc-sys:system/oc-sys:aaa/oc-sys:server-groups/oc-sys:server-group/oc-sys:servers/oc-sys:server/oc-sys:config/oc-sys:timeout {
      deviate add {
      }
    }

    deviation /oc-sys:system/oc-sys:aaa/oc-sys:server-groups/oc-sys:server-group/oc-sys:servers/oc-sys:server/oc-sys:config/oc-sys:name {
      deviate add {
      }
    }

    deviation /oc-sys:system/oc-sys:aaa/oc-sys:server-groups/oc-sys:server-group/oc-sys:servers/oc-sys:server/oc-sys:config/oc-sys:address {
      deviate add {
      }
    }

    deviation /oc-sys:system/oc-sys:aaa/oc-sys:server-groups/oc-sys:server-group/oc-sys:servers/oc-sys:server/oc-sys:state {
      deviate add {
      }
    }

    deviation /oc-sys:system/oc-sys:aaa/oc-sys:server-groups/oc-sys:server-group/oc-sys:servers/oc-sys:server/oc-sys:state/oc-sys:messages-sent {
      deviate add {
      }
    }

    deviation /oc-sys:system/oc-sys:aaa/oc-sys:server-groups/oc-sys:server-group/oc-sys:servers/oc-sys:server/oc-sys:state/oc-sys:messages-received {
      deviate add {
      }
    }

    deviation /oc-sys:system/oc-sys:aaa/oc-sys:server-groups/oc-sys:server-group/oc-sys:servers/oc-sys:server/oc-sys:state/oc-sys:connection-opens {
      deviate add {
      }
    }

    deviation /oc-sys:system/oc-sys:aaa/oc-sys:server-groups/oc-sys:server-group/oc-sys:servers/oc-sys:server/oc-sys:state/oc-sys:connection-closes {
      deviate add {
      }
    }

    deviation /oc-sys:system/oc-sys:aaa/oc-sys:server-groups/oc-sys:server-group/oc-sys:servers/oc-sys:server/oc-sys:state/oc-sys:timeout {
      deviate add {
      }
    }

    deviation /oc-sys:system/oc-sys:aaa/oc-sys:server-groups/oc-sys:server-group/oc-sys:servers/oc-sys:server/oc-sys:state/oc-sys:connection-timeouts {
      deviate add {
      }
    }

    deviation /oc-sys:system/oc-sys:aaa/oc-sys:server-groups/oc-sys:server-group/oc-sys:servers/oc-sys:server/oc-sys:state/oc-sys:errors-received {
      deviate add {
      }
    }

    deviation /oc-sys:system/oc-sys:aaa/oc-sys:server-groups/oc-sys:server-group/oc-sys:servers/oc-sys:server/oc-sys:state/oc-sys:connection-failures {
      deviate add {
      }
    }

    deviation /oc-sys:system/oc-sys:aaa/oc-sys:server-groups/oc-sys:server-group/oc-sys:servers/oc-sys:server/oc-sys:state/oc-sys:address {
      deviate add {
      }
    }

    deviation /oc-sys:system/oc-sys:aaa/oc-sys:server-groups/oc-sys:server-group/oc-sys:servers/oc-sys:server/oc-sys:state/oc-sys:name {
      deviate add {
      }
    }

    deviation /oc-sys:system/oc-sys:aaa/oc-sys:server-groups/oc-sys:server-group/oc-sys:servers/oc-sys:server/oc-sys:state/oc-sys:connection-aborts {
      deviate add {
      }
    }

    deviation /oc-sys:system/oc-sys:aaa/oc-sys:server-groups/oc-sys:server-group/oc-sys:name {
      deviate add {
      }
    }

    deviation /oc-sys:system/oc-sys:aaa/oc-sys:server-groups/oc-sys:server-group/oc-sys:config {
      deviate add {
      }
    }

    deviation /oc-sys:system/oc-sys:aaa/oc-sys:server-groups/oc-sys:server-group/oc-sys:config/oc-sys:name {
      deviate add {
      }
    }

    deviation /oc-sys:system/oc-sys:aaa/oc-sys:server-groups/oc-sys:server-group/oc-sys:config/oc-sys:type {
      deviate add {
      }
    }

    deviation /oc-sys:system/oc-sys:aaa/oc-sys:server-groups/oc-sys:server-group/oc-sys:state {
      deviate add {
      }
    }

    deviation /oc-sys:system/oc-sys:aaa/oc-sys:server-groups/oc-sys:server-group/oc-sys:state/oc-sys:type {
      deviate add {
      }
    }

    deviation /oc-sys:system/oc-sys:aaa/oc-sys:server-groups/oc-sys:server-group/oc-sys:state/oc-sys:name {
      deviate add {
      }
    }

    deviation /oc-sys:system/oc-sys:aaa/oc-sys:config {
      deviate add {
      }
    }

    deviation /oc-sys:system/oc-sys:aaa/oc-sys:state {
      deviate add {
      }
    }

    deviation /oc-sys:system/oc-sys:aaa/oc-sys:authentication {
      deviate add {
      }
    }

    deviation /oc-sys:system/oc-sys:aaa/oc-sys:authentication/oc-sys:admin-user {
      deviate add {
      }
    }

    deviation /oc-sys:system/oc-sys:aaa/oc-sys:authentication/oc-sys:admin-user/oc-sys:state {
      deviate add {
      }
    }

    deviation /oc-sys:system/oc-sys:aaa/oc-sys:authentication/oc-sys:admin-user/oc-sys:state/oc-sys:admin-password {
      deviate add {
      }
    }

    deviation /oc-sys:system/oc-sys:aaa/oc-sys:authentication/oc-sys:admin-user/oc-sys:state/oc-sys:admin-password-hashed {
      deviate add {
      }
    }

    deviation /oc-sys:system/oc-sys:aaa/oc-sys:authentication/oc-sys:admin-user/oc-sys:state/oc-sys:admin-username {
      deviate add {
      }
    }

    deviation /oc-sys:system/oc-sys:aaa/oc-sys:authentication/oc-sys:admin-user/oc-sys:config {
      deviate add {
      }
    }

    deviation /oc-sys:system/oc-sys:aaa/oc-sys:authentication/oc-sys:admin-user/oc-sys:config/oc-sys:admin-password-hashed {
      deviate add {
      }
    }

    deviation /oc-sys:system/oc-sys:aaa/oc-sys:authentication/oc-sys:admin-user/oc-sys:config/oc-sys:admin-password {
      deviate add {
      }
    }

    deviation /oc-sys:system/oc-sys:aaa/oc-sys:authentication/oc-sys:users {
      deviate add {
      }
    }

    deviation /oc-sys:system/oc-sys:aaa/oc-sys:authentication/oc-sys:users/oc-sys:user {
      deviate add {
      }
    }

    deviation /oc-sys:system/oc-sys:aaa/oc-sys:authentication/oc-sys:users/oc-sys:user/oc-sys:username {
      deviate add {
      }
    }

    deviation /oc-sys:system/oc-sys:aaa/oc-sys:authentication/oc-sys:users/oc-sys:user/oc-sys:config {
      deviate add {
      }
    }

    deviation /oc-sys:system/oc-sys:aaa/oc-sys:authentication/oc-sys:users/oc-sys:user/oc-sys:config/oc-sys:ssh-key {
      deviate add {
      }
    }

    deviation /oc-sys:system/oc-sys:aaa/oc-sys:authentication/oc-sys:users/oc-sys:user/oc-sys:config/oc-sys:role {
      deviate add {
      }
    }

    deviation /oc-sys:system/oc-sys:aaa/oc-sys:authentication/oc-sys:users/oc-sys:user/oc-sys:config/oc-sys:username {
      deviate add {
      }
    }

    deviation /oc-sys:system/oc-sys:aaa/oc-sys:authentication/oc-sys:users/oc-sys:user/oc-sys:config/oc-sys:password {
      deviate add {
      }
    }

    deviation /oc-sys:system/oc-sys:aaa/oc-sys:authentication/oc-sys:users/oc-sys:user/oc-sys:config/oc-sys:password-hashed {
      deviate add {
      }
    }

    deviation /oc-sys:system/oc-sys:aaa/oc-sys:authentication/oc-sys:users/oc-sys:user/oc-sys:state {
      deviate add {
      }
    }

    deviation /oc-sys:system/oc-sys:aaa/oc-sys:authentication/oc-sys:users/oc-sys:user/oc-sys:state/oc-sys:ssh-key {
      deviate add {
      }
    }

    deviation /oc-sys:system/oc-sys:aaa/oc-sys:authentication/oc-sys:users/oc-sys:user/oc-sys:state/oc-sys:role {
      deviate add {
      }
    }

    deviation /oc-sys:system/oc-sys:aaa/oc-sys:authentication/oc-sys:users/oc-sys:user/oc-sys:state/oc-sys:username {
      deviate add {
      }
    }

    deviation /oc-sys:system/oc-sys:aaa/oc-sys:authentication/oc-sys:users/oc-sys:user/oc-sys:state/oc-sys:password {
      deviate add {
      }
    }

    deviation /oc-sys:system/oc-sys:aaa/oc-sys:authentication/oc-sys:users/oc-sys:user/oc-sys:state/oc-sys:password-hashed {
      deviate add {
      }
    }

    deviation /oc-sys:system/oc-sys:aaa/oc-sys:authentication/oc-sys:config {
      deviate add {
      }
    }

    deviation /oc-sys:system/oc-sys:aaa/oc-sys:authentication/oc-sys:config/oc-sys:authentication-method {
      deviate add {
      }
    }

    deviation /oc-sys:system/oc-sys:aaa/oc-sys:authentication/oc-sys:state {
      deviate add {
      }
    }

    deviation /oc-sys:system/oc-sys:aaa/oc-sys:authentication/oc-sys:state/oc-sys:authentication-method {
      deviate add {
      }
    }

    deviation /oc-sys:system/oc-sys:aaa/oc-sys:authorization {
      deviate add {
      }
    }

    deviation /oc-sys:system/oc-sys:aaa/oc-sys:authorization/oc-sys:config {
      deviate add {
      }
    }

    deviation /oc-sys:system/oc-sys:aaa/oc-sys:authorization/oc-sys:config/oc-sys:authorization-method {
      deviate add {
      }
    }

    deviation /oc-sys:system/oc-sys:aaa/oc-sys:authorization/oc-sys:state {
      deviate add {
      }
    }

    deviation /oc-sys:system/oc-sys:aaa/oc-sys:authorization/oc-sys:state/oc-sys:authorization-method {
      deviate add {
      }
    }

    deviation /oc-sys:system/oc-sys:aaa/oc-sys:authorization/oc-sys:events {
      deviate add {
      }
    }

    deviation /oc-sys:system/oc-sys:aaa/oc-sys:authorization/oc-sys:events/oc-sys:event {
      deviate add {
      }
    }

    deviation /oc-sys:system/oc-sys:aaa/oc-sys:authorization/oc-sys:events/oc-sys:event/oc-sys:event-type {
      deviate add {
      }
    }

    deviation /oc-sys:system/oc-sys:aaa/oc-sys:authorization/oc-sys:events/oc-sys:event/oc-sys:config {
      deviate add {
      }
    }

    deviation /oc-sys:system/oc-sys:aaa/oc-sys:authorization/oc-sys:events/oc-sys:event/oc-sys:config/oc-sys:event-type {
      deviate add {
      }
    }

    deviation /oc-sys:system/oc-sys:aaa/oc-sys:authorization/oc-sys:events/oc-sys:event/oc-sys:state {
      deviate add {
      }
    }

    deviation /oc-sys:system/oc-sys:aaa/oc-sys:authorization/oc-sys:events/oc-sys:event/oc-sys:state/oc-sys:event-type {
      deviate add {
      }
    }

    deviation /oc-sys:system/oc-sys:messages {
      deviate add {
      }
    }

    deviation /oc-sys:system/oc-sys:messages/oc-sys:debug-entries {
      deviate add {
      }
    }

    deviation /oc-sys:system/oc-sys:messages/oc-sys:debug-entries/oc-sys:debug-service {
      deviate add {
      }
    }

    deviation /oc-sys:system/oc-sys:messages/oc-sys:debug-entries/oc-sys:debug-service/oc-sys:config {
      deviate add {
      }
    }

    deviation /oc-sys:system/oc-sys:messages/oc-sys:debug-entries/oc-sys:debug-service/oc-sys:config/oc-sys:service {
      deviate add {
      }
    }

    deviation /oc-sys:system/oc-sys:messages/oc-sys:debug-entries/oc-sys:debug-service/oc-sys:config/oc-sys:enabled {
      deviate add {
      }
    }

    deviation /oc-sys:system/oc-sys:messages/oc-sys:debug-entries/oc-sys:debug-service/oc-sys:state {
      deviate add {
      }
    }

    deviation /oc-sys:system/oc-sys:messages/oc-sys:debug-entries/oc-sys:debug-service/oc-sys:state/oc-sys:enabled {
      deviate add {
      }
    }

    deviation /oc-sys:system/oc-sys:messages/oc-sys:debug-entries/oc-sys:debug-service/oc-sys:state/oc-sys:service {
      deviate add {
      }
    }

    deviation /oc-sys:system/oc-sys:messages/oc-sys:debug-entries/oc-sys:debug-service/oc-sys:service {
      deviate add {
      }
    }

    deviation /oc-sys:system/oc-sys:messages/oc-sys:config {
      deviate add {
      }
    }

    deviation /oc-sys:system/oc-sys:messages/oc-sys:config/oc-sys:severity {
      deviate add {
      }
    }

    deviation /oc-sys:system/oc-sys:messages/oc-sys:state {
      deviate add {
      }
    }

    deviation /oc-sys:system/oc-sys:messages/oc-sys:state/oc-sys:message {
      deviate add {
      }
    }

    deviation /oc-sys:system/oc-sys:messages/oc-sys:state/oc-sys:message/oc-sys:msgid {
      deviate add {
      }
    }

    deviation /oc-sys:system/oc-sys:messages/oc-sys:state/oc-sys:message/oc-sys:msg {
      deviate add {
      }
    }

    deviation /oc-sys:system/oc-sys:messages/oc-sys:state/oc-sys:message/oc-sys:priority {
      deviate add {
      }
    }

    deviation /oc-sys:system/oc-sys:messages/oc-sys:state/oc-sys:message/oc-sys:app-name {
      deviate add {
      }
    }

    deviation /oc-sys:system/oc-sys:messages/oc-sys:state/oc-sys:message/oc-sys:procid {
      deviate add {
      }
    }

    deviation /oc-sys:system/oc-sys:messages/oc-sys:state/oc-sys:severity {
      deviate add {
      }
    }

    deviation /oc-sys:system/oc-sys:logging {
      deviate add {
      }
    }

    deviation /oc-sys:system/oc-sys:logging/oc-sys:console {
      deviate add {
      }
    }

    deviation /oc-sys:system/oc-sys:logging/oc-sys:console/oc-sys:selectors {
      deviate add {
      }
    }

    deviation /oc-sys:system/oc-sys:logging/oc-sys:console/oc-sys:selectors/oc-sys:selector {
      deviate add {
      }
    }

    deviation /oc-sys:system/oc-sys:logging/oc-sys:console/oc-sys:selectors/oc-sys:selector/oc-sys:severity {
      deviate add {
      }
    }

    deviation /oc-sys:system/oc-sys:logging/oc-sys:console/oc-sys:selectors/oc-sys:selector/oc-sys:config {
      deviate add {
      }
    }

    deviation /oc-sys:system/oc-sys:logging/oc-sys:console/oc-sys:selectors/oc-sys:selector/oc-sys:config/oc-sys:severity {
      deviate add {
      }
    }

    deviation /oc-sys:system/oc-sys:logging/oc-sys:console/oc-sys:selectors/oc-sys:selector/oc-sys:config/oc-sys:facility {
      deviate add {
      }
    }

    deviation /oc-sys:system/oc-sys:logging/oc-sys:console/oc-sys:selectors/oc-sys:selector/oc-sys:state {
      deviate add {
      }
    }

    deviation /oc-sys:system/oc-sys:logging/oc-sys:console/oc-sys:selectors/oc-sys:selector/oc-sys:state/oc-sys:severity {
      deviate add {
      }
    }

    deviation /oc-sys:system/oc-sys:logging/oc-sys:console/oc-sys:selectors/oc-sys:selector/oc-sys:state/oc-sys:facility {
      deviate add {
      }
    }

    deviation /oc-sys:system/oc-sys:logging/oc-sys:console/oc-sys:selectors/oc-sys:selector/oc-sys:facility {
      deviate add {
      }
    }

    deviation /oc-sys:system/oc-sys:logging/oc-sys:console/oc-sys:config {
      deviate add {
      }
    }

    deviation /oc-sys:system/oc-sys:logging/oc-sys:console/oc-sys:state {
      deviate add {
      }
    }

    deviation /oc-sys:system/oc-sys:logging/oc-sys:remote-servers {
      deviate add {
      }
    }

    deviation /oc-sys:system/oc-sys:logging/oc-sys:remote-servers/oc-sys:remote-server {
      deviate add {
      }
    }

    deviation /oc-sys:system/oc-sys:logging/oc-sys:remote-servers/oc-sys:remote-server/oc-sys:selectors {
      deviate add {
      }
    }

    deviation /oc-sys:system/oc-sys:logging/oc-sys:remote-servers/oc-sys:remote-server/oc-sys:selectors/oc-sys:selector {
      deviate add {
      }
    }

    deviation /oc-sys:system/oc-sys:logging/oc-sys:remote-servers/oc-sys:remote-server/oc-sys:selectors/oc-sys:selector/oc-sys:facility {
      deviate add {
      }
    }

    deviation /oc-sys:system/oc-sys:logging/oc-sys:remote-servers/oc-sys:remote-server/oc-sys:selectors/oc-sys:selector/oc-sys:severity {
      deviate add {
      }
    }

    deviation /oc-sys:system/oc-sys:logging/oc-sys:remote-servers/oc-sys:remote-server/oc-sys:selectors/oc-sys:selector/oc-sys:config {
      deviate add {
      }
    }

    deviation /oc-sys:system/oc-sys:logging/oc-sys:remote-servers/oc-sys:remote-server/oc-sys:selectors/oc-sys:selector/oc-sys:config/oc-sys:facility {
      deviate add {
      }
    }

    deviation /oc-sys:system/oc-sys:logging/oc-sys:remote-servers/oc-sys:remote-server/oc-sys:selectors/oc-sys:selector/oc-sys:config/oc-sys:severity {
      deviate add {
      }
    }

    deviation /oc-sys:system/oc-sys:logging/oc-sys:remote-servers/oc-sys:remote-server/oc-sys:selectors/oc-sys:selector/oc-sys:state {
      deviate add {
      }
    }

    deviation /oc-sys:system/oc-sys:logging/oc-sys:remote-servers/oc-sys:remote-server/oc-sys:selectors/oc-sys:selector/oc-sys:state/oc-sys:severity {
      deviate add {
      }
    }

    deviation /oc-sys:system/oc-sys:logging/oc-sys:remote-servers/oc-sys:remote-server/oc-sys:selectors/oc-sys:selector/oc-sys:state/oc-sys:facility {
      deviate add {
      }
    }

    deviation /oc-sys:system/oc-sys:logging/oc-sys:remote-servers/oc-sys:remote-server/oc-sys:host {
      deviate add {
      }
    }

    deviation /oc-sys:system/oc-sys:logging/oc-sys:remote-servers/oc-sys:remote-server/oc-sys:config {
      deviate add {
      }
    }

    deviation /oc-sys:system/oc-sys:logging/oc-sys:remote-servers/oc-sys:remote-server/oc-sys:config/oc-sys:host {
      deviate add {
      }
    }

    deviation /oc-sys:system/oc-sys:logging/oc-sys:remote-servers/oc-sys:remote-server/oc-sys:config/oc-sys:source-address {
      deviate add {
      }
    }

    deviation /oc-sys:system/oc-sys:logging/oc-sys:remote-servers/oc-sys:remote-server/oc-sys:config/oc-sys:remote-port {
      deviate add {
      }
    }

    deviation /oc-sys:system/oc-sys:logging/oc-sys:remote-servers/oc-sys:remote-server/oc-sys:state {
      deviate add {
      }
    }

    deviation /oc-sys:system/oc-sys:logging/oc-sys:remote-servers/oc-sys:remote-server/oc-sys:state/oc-sys:remote-port {
      deviate add {
      }
    }

    deviation /oc-sys:system/oc-sys:logging/oc-sys:remote-servers/oc-sys:remote-server/oc-sys:state/oc-sys:host {
      deviate add {
      }
    }

    deviation /oc-sys:system/oc-sys:logging/oc-sys:remote-servers/oc-sys:remote-server/oc-sys:state/oc-sys:source-address {
      deviate add {
      }
    }

}
