module openconfig-terminal-device-annot {

    yang-version "1";

    namespace "http://openconfig.net/yang/annotation/oc-terminal-device-annot";
    prefix "oc-terminal-device-annot";

    import sonic-extensions { prefix sonic-ext; }
    import openconfig-if-ethernet { prefix oc-eth; }
    import openconfig-interfaces { prefix oc-if; }
    import openconfig-lldp { prefix oc-lldp; }
    import ietf-yang-types { prefix yang; }
    import openconfig-extensions { prefix oc-ext; }
    import openconfig-yang-types { prefix oc-yang; }
    import openconfig-types { prefix oc-types; }
    import openconfig-transport-types { prefix oc-opt-types; }
    import openconfig-platform { prefix oc-platform; }
    import openconfig-platform-transceiver { prefix oc-transceiver; }
    import openconfig-terminal-device { prefix oc-opt-term; }

    deviation /oc-opt-term:terminal-device {
	    deviate add {	   
		    sonic-ext:subscribe-on-change "enable";
		    sonic-ext:post-transformer "terminal_device_post_xfmr";
		    sonic-ext:get-namespace "td_get_namespace_xfmr";
	    }
    }

    deviation /oc-opt-term:terminal-device/oc-opt-term:logical-channels {
      deviate add {	   
	      sonic-ext:table-name "LOGICAL_CHANNEL";
      }
    }

    deviation /oc-opt-term:terminal-device/oc-opt-term:logical-channels/oc-opt-term:channel {
      deviate add {
	      sonic-ext:key-transformer "logical_channel_key_xfmr";
      }
    }

    deviation /oc-opt-term:terminal-device/oc-opt-term:logical-channels/oc-opt-term:channel/oc-opt-term:index {
      deviate add {
      }
    }

    deviation /oc-opt-term:terminal-device/oc-opt-term:logical-channels/oc-opt-term:channel/oc-opt-term:config {
      deviate add {
      }
    }

    deviation /oc-opt-term:terminal-device/oc-opt-term:logical-channels/oc-opt-term:channel/oc-opt-term:config/oc-opt-term:logical-channel-type {
      deviate add {
      }
    }

    deviation /oc-opt-term:terminal-device/oc-opt-term:logical-channels/oc-opt-term:channel/oc-opt-term:config/oc-opt-term:description {
      deviate add {
      }
    }

    deviation /oc-opt-term:terminal-device/oc-opt-term:logical-channels/oc-opt-term:channel/oc-opt-term:config/oc-opt-term:test-signal {
      deviate add {
	    sonic-ext:field-name "test-signal";
      }
    }

    deviation /oc-opt-term:terminal-device/oc-opt-term:logical-channels/oc-opt-term:channel/oc-opt-term:config/oc-opt-term:loopback-mode {
      deviate add {
	    sonic-ext:field-name "loopback-mode";
      }
    }

    deviation /oc-opt-term:terminal-device/oc-opt-term:logical-channels/oc-opt-term:channel/oc-opt-term:config/oc-opt-term:admin-state {
      deviate add {
	    sonic-ext:field-name "admin-state";
      }
    }

    deviation /oc-opt-term:terminal-device/oc-opt-term:logical-channels/oc-opt-term:channel/oc-opt-term:config/oc-opt-term:client-mapping-mode {
      deviate add {
      }
    }

    deviation /oc-opt-term:terminal-device/oc-opt-term:logical-channels/oc-opt-term:channel/oc-opt-term:config/oc-opt-term:trib-protocol {
      deviate add {
      }
    }

    deviation /oc-opt-term:terminal-device/oc-opt-term:logical-channels/oc-opt-term:channel/oc-opt-term:config/oc-opt-term:index {
      deviate add {
	    sonic-ext:field-transformer "logical_channel_field_xfmr";	   
      }
    }

    deviation /oc-opt-term:terminal-device/oc-opt-term:logical-channels/oc-opt-term:channel/oc-opt-term:config/oc-opt-term:rate-class {
      deviate add {
      }
    }

    deviation /oc-opt-term:terminal-device/oc-opt-term:logical-channels/oc-opt-term:channel/oc-opt-term:state {
      deviate add {
	      sonic-ext:db-name "STATE_DB";
	      sonic-ext:table-name "LOGICAL_CHANNEL_TABLE";
	      sonic-ext:key-transformer "logical_channel_key_xfmr";
      }
    }

    deviation /oc-opt-term:terminal-device/oc-opt-term:logical-channels/oc-opt-term:channel/oc-opt-term:state/oc-opt-term:rate-class {
      deviate add {
	    sonic-ext:field-name "rate-class";
      }
    }

    deviation /oc-opt-term:terminal-device/oc-opt-term:logical-channels/oc-opt-term:channel/oc-opt-term:state/oc-opt-term:description {
      deviate add {
	    sonic-ext:field-name "description";
      }
    }

    deviation /oc-opt-term:terminal-device/oc-opt-term:logical-channels/oc-opt-term:channel/oc-opt-term:state/oc-opt-term:logical-channel-type {
      deviate add {
	    sonic-ext:field-name "logical-channel-type";
      }
    }

    deviation /oc-opt-term:terminal-device/oc-opt-term:logical-channels/oc-opt-term:channel/oc-opt-term:state/oc-opt-term:test-signal {
      deviate add {
	    sonic-ext:field-name "test-signal";
      }
    }

    deviation /oc-opt-term:terminal-device/oc-opt-term:logical-channels/oc-opt-term:channel/oc-opt-term:state/oc-opt-term:loopback-mode {
      deviate add {
	    sonic-ext:field-name "loopback-mode";
      }
    }

    deviation /oc-opt-term:terminal-device/oc-opt-term:logical-channels/oc-opt-term:channel/oc-opt-term:state/oc-opt-term:admin-state {
      deviate add {
	    sonic-ext:field-name "admin-state";
      }
    }

    deviation /oc-opt-term:terminal-device/oc-opt-term:logical-channels/oc-opt-term:channel/oc-opt-term:state/oc-opt-term:trib-protocol {
      deviate add {
	    sonic-ext:field-name "trib-protocol";
      }
    }

    deviation /oc-opt-term:terminal-device/oc-opt-term:logical-channels/oc-opt-term:channel/oc-opt-term:state/oc-opt-term:client-mapping-mode {
      deviate add {
      }
    }

    deviation /oc-opt-term:terminal-device/oc-opt-term:logical-channels/oc-opt-term:channel/oc-opt-term:state/oc-opt-term:link-state {
      deviate add {
	    sonic-ext:field-name "link-state";
      }
    }

    deviation /oc-opt-term:terminal-device/oc-opt-term:logical-channels/oc-opt-term:channel/oc-opt-term:state/oc-opt-term:index {
      deviate add {
	    sonic-ext:field-transformer "logical_channel_field_xfmr";
      }
    }

    deviation /oc-opt-term:terminal-device/oc-opt-term:logical-channels/oc-opt-term:channel/oc-opt-term:ethernet {
      deviate add {
	      sonic-ext:table-name "ETHERNET";
	      sonic-ext:key-transformer "logical_channel_key_xfmr";
      }
    }

    deviation /oc-opt-term:terminal-device/oc-opt-term:logical-channels/oc-opt-term:channel/oc-opt-term:ethernet/oc-opt-term:config {
      deviate add {
      }
    }

    deviation /oc-opt-term:terminal-device/oc-opt-term:logical-channels/oc-opt-term:channel/oc-opt-term:ethernet/oc-opt-term:config/oc-opt-term:client-als {
      deviate add {
	    sonic-ext:field-name "client-als";	  
      }
    }


    deviation /oc-opt-term:terminal-device/oc-opt-term:logical-channels/oc-opt-term:channel/oc-opt-term:ethernet/oc-opt-term:config/oc-opt-term:als-delay {
      deviate add {
	    sonic-ext:field-name "als-delay";
      }
    }

    deviation /oc-opt-term:terminal-device/oc-opt-term:logical-channels/oc-opt-term:channel/oc-opt-term:ethernet/oc-opt-term:state {
      deviate add {
	      sonic-ext:subtree-transformer "ethernet_subtree_xfmr";
              sonic-ext:subscribe-on-change "enable";
      }
    }

    deviation /oc-opt-term:terminal-device/oc-opt-term:logical-channels/oc-opt-term:channel/oc-opt-term:ethernet/oc-opt-term:state/oc-opt-term:in-8021q-frames {
      deviate add {
      }
    }

    deviation /oc-opt-term:terminal-device/oc-opt-term:logical-channels/oc-opt-term:channel/oc-opt-term:ethernet/oc-opt-term:state/oc-opt-term:in-pcs-errored-seconds {
      deviate add {
      }
    }

    deviation /oc-opt-term:terminal-device/oc-opt-term:logical-channels/oc-opt-term:channel/oc-opt-term:ethernet/oc-opt-term:state/oc-opt-term:out-pcs-bip-errors {
      deviate add {
      }
    }

    deviation /oc-opt-term:terminal-device/oc-opt-term:logical-channels/oc-opt-term:channel/oc-opt-term:ethernet/oc-opt-term:state/oc-opt-term:in-block-errors {
      deviate add {
      }
    }

    deviation /oc-opt-term:terminal-device/oc-opt-term:logical-channels/oc-opt-term:channel/oc-opt-term:ethernet/oc-opt-term:state/oc-opt-term:fec-uncorrectable-blocks {
      deviate add {
      }
    }

    deviation /oc-opt-term:terminal-device/oc-opt-term:logical-channels/oc-opt-term:channel/oc-opt-term:ethernet/oc-opt-term:state/oc-opt-term:out-block-errors {
      deviate add {
      }
    }

    deviation /oc-opt-term:terminal-device/oc-opt-term:logical-channels/oc-opt-term:channel/oc-opt-term:ethernet/oc-opt-term:state/oc-opt-term:in-pcs-severely-errored-seconds {
      deviate add {
      }
    }

    deviation /oc-opt-term:terminal-device/oc-opt-term:logical-channels/oc-opt-term:channel/oc-opt-term:ethernet/oc-opt-term:state/oc-opt-term:in-mac-control-frames {
      deviate add {
      }
    }

    deviation /oc-opt-term:terminal-device/oc-opt-term:logical-channels/oc-opt-term:channel/oc-opt-term:ethernet/oc-opt-term:state/oc-opt-term:in-pcs-bip-errors {
      deviate add {
      }
    }

    deviation /oc-opt-term:terminal-device/oc-opt-term:logical-channels/oc-opt-term:channel/oc-opt-term:ethernet/oc-opt-term:state/oc-opt-term:in-jabber-frames {
      deviate add {
      }
    }

    deviation /oc-opt-term:terminal-device/oc-opt-term:logical-channels/oc-opt-term:channel/oc-opt-term:ethernet/oc-opt-term:state/oc-opt-term:out-mac-pause-frames {
      deviate add {
      }
    }

    deviation /oc-opt-term:terminal-device/oc-opt-term:logical-channels/oc-opt-term:channel/oc-opt-term:ethernet/oc-opt-term:state/oc-opt-term:esnr {
      deviate add {
      }
    }

    deviation /oc-opt-term:terminal-device/oc-opt-term:logical-channels/oc-opt-term:channel/oc-opt-term:ethernet/oc-opt-term:state/oc-opt-term:esnr/oc-opt-term:min-time {
      deviate add {
      }
    }

    deviation /oc-opt-term:terminal-device/oc-opt-term:logical-channels/oc-opt-term:channel/oc-opt-term:ethernet/oc-opt-term:state/oc-opt-term:esnr/oc-opt-term:max-time {
      deviate add {
      }
    }

    deviation /oc-opt-term:terminal-device/oc-opt-term:logical-channels/oc-opt-term:channel/oc-opt-term:ethernet/oc-opt-term:state/oc-opt-term:esnr/oc-opt-term:instant {
      deviate add {
      }
    }

    deviation /oc-opt-term:terminal-device/oc-opt-term:logical-channels/oc-opt-term:channel/oc-opt-term:ethernet/oc-opt-term:state/oc-opt-term:esnr/oc-opt-term:avg {
      deviate add {
      }
    }

    deviation /oc-opt-term:terminal-device/oc-opt-term:logical-channels/oc-opt-term:channel/oc-opt-term:ethernet/oc-opt-term:state/oc-opt-term:esnr/oc-opt-term:min {
      deviate add {
      }
    }

    deviation /oc-opt-term:terminal-device/oc-opt-term:logical-channels/oc-opt-term:channel/oc-opt-term:ethernet/oc-opt-term:state/oc-opt-term:esnr/oc-opt-term:max {
      deviate add {
      }
    }

    deviation /oc-opt-term:terminal-device/oc-opt-term:logical-channels/oc-opt-term:channel/oc-opt-term:ethernet/oc-opt-term:state/oc-opt-term:esnr/oc-opt-term:interval {
      deviate add {
      }
    }

    deviation /oc-opt-term:terminal-device/oc-opt-term:logical-channels/oc-opt-term:channel/oc-opt-term:ethernet/oc-opt-term:state/oc-opt-term:in-fragment-frames {
	    deviate add {
	    }
    }

   
    deviation /oc-opt-term:terminal-device/oc-opt-term:logical-channels/oc-opt-term:channel/oc-opt-term:ethernet/oc-opt-term:state/oc-opt-term:als-delay {
      deviate add {
      }
    }

    deviation /oc-opt-term:terminal-device/oc-opt-term:logical-channels/oc-opt-term:channel/oc-opt-term:ethernet/oc-opt-term:state/oc-opt-term:client-als {
      deviate add {
      }
    }

    deviation /oc-opt-term:terminal-device/oc-opt-term:logical-channels/oc-opt-term:channel/oc-opt-term:config/oc-opt-term:description {
      deviate add {
	    sonic-ext:field-name "description";
		// not found in schema but present in config_db.json in sonic-utilities
      }
    }

    deviation /oc-opt-term:terminal-device/oc-opt-term:logical-channels/oc-opt-term:channel/oc-opt-term:config/oc-opt-term:test-signal {
      deviate add {
	    sonic-ext:field-name "test-signal";
      }
    }

    deviation /oc-opt-term:terminal-device/oc-opt-term:logical-channels/oc-opt-term:channel/oc-opt-term:config/oc-opt-term:loopback-mode {
      deviate add {
	    sonic-ext:field-name "loopback-mode";
      }
    }

    deviation /oc-opt-term:terminal-device/oc-opt-term:logical-channels/oc-opt-term:channel/oc-opt-term:config/oc-opt-term:admin-state {
      deviate add {
	    sonic-ext:field-name "admin-state";
      }
    }


    deviation /oc-opt-term:terminal-device/oc-opt-term:logical-channels/oc-opt-term:channel/oc-opt-term:state {
      deviate add {
	    sonic-ext:db-name "STATE_DB";
		sonic-ext:table-name "LOGICAL_CHANNEL_TABLE";
		sonic-ext:key-transformer "logical_channel_key_xfmr";
      }
    }

    deviation /oc-opt-term:terminal-device/oc-opt-term:logical-channels/oc-opt-term:channel/oc-opt-term:state/oc-opt-term:rate-class {
      deviate add {
	    sonic-ext:field-name "rate-class";
      }
    }

    deviation /oc-opt-term:terminal-device/oc-opt-term:logical-channels/oc-opt-term:channel/oc-opt-term:state/oc-opt-term:description {
      deviate add {
	    sonic-ext:field-name "description";
      }
    }

    deviation /oc-opt-term:terminal-device/oc-opt-term:logical-channels/oc-opt-term:channel/oc-opt-term:state/oc-opt-term:logical-channel-type {
      deviate add {
	    sonic-ext:field-name "logical-channel-type";
      }
    }

    deviation /oc-opt-term:terminal-device/oc-opt-term:logical-channels/oc-opt-term:channel/oc-opt-term:state/oc-opt-term:test-signal {
      deviate add {
	    sonic-ext:field-name "test-signal";
      }
    }

    deviation /oc-opt-term:terminal-device/oc-opt-term:logical-channels/oc-opt-term:channel/oc-opt-term:state/oc-opt-term:loopback-mode {
      deviate add {
	    sonic-ext:field-name "loopback-mode";
      }
    }

    deviation /oc-opt-term:terminal-device/oc-opt-term:logical-channels/oc-opt-term:channel/oc-opt-term:state/oc-opt-term:admin-state {
      deviate add {
	    sonic-ext:field-name "admin-state";
      }
    }

    deviation /oc-opt-term:terminal-device/oc-opt-term:logical-channels/oc-opt-term:channel/oc-opt-term:state/oc-opt-term:trib-protocol {
      deviate add {
	    sonic-ext:field-name "trib-protocol";
      }
    }

    deviation /oc-opt-term:terminal-device/oc-opt-term:logical-channels/oc-opt-term:channel/oc-opt-term:state/oc-opt-term:link-state {
      deviate add {
	    sonic-ext:field-name "link-state";
      }
    }

    deviation /oc-opt-term:terminal-device/oc-opt-term:logical-channels/oc-opt-term:channel/oc-opt-term:ethernet/oc-opt-term:lldp {
      deviate add {
	      sonic-ext:db-name "STATE_DB";
	      sonic-ext:table-name "LLDP_TABLE";	
	      sonic-ext:key-transformer "logical_channel_key_xfmr";
      }
    }

	deviation /oc-opt-term:terminal-device/oc-opt-term:logical-channels/oc-opt-term:channel/oc-opt-term:ethernet/oc-opt-term:lldp/oc-opt-term:config {
      deviate add {
      }
    }

	
	deviation /oc-opt-term:terminal-device/oc-opt-term:logical-channels/oc-opt-term:channel/oc-opt-term:ethernet/oc-opt-term:lldp/oc-opt-term:state/oc-opt-term:enabled {
      deviate add {
	    sonic-ext:field-name "enabled";
      }
    }

    deviation /oc-opt-term:terminal-device/oc-opt-term:logical-channels/oc-opt-term:channel/oc-opt-term:ethernet/oc-opt-term:lldp/oc-opt-term:state/oc-opt-term:snooping {
      deviate add {
	    sonic-ext:field-name "snooping";
      }
    }

    deviation /oc-opt-term:terminal-device/oc-opt-term:logical-channels/oc-opt-term:channel/oc-opt-term:ethernet/oc-opt-term:lldp/oc-opt-term:neighbors {
      deviate add {
        sonic-ext:db-name "STATE_DB";
      }
    }

    deviation /oc-opt-term:terminal-device/oc-opt-term:logical-channels/oc-opt-term:channel/oc-opt-term:ethernet/oc-opt-term:lldp/oc-opt-term:neighbors/oc-opt-term:neighbor {
      deviate add {
	      sonic-ext:db-name "STATE_DB";
	      sonic-ext:table-name "NEIGHBOR_TABLE";
	      sonic-ext:key-transformer "neighbor_key_xfmr";
      }
    }

    deviation /oc-opt-term:terminal-device/oc-opt-term:logical-channels/oc-opt-term:channel/oc-opt-term:ethernet/oc-opt-term:lldp/oc-opt-term:neighbors/oc-opt-term:neighbor/oc-opt-term:config {
      deviate add {
      }
    }

    deviation /oc-opt-term:terminal-device/oc-opt-term:logical-channels/oc-opt-term:channel/oc-opt-term:ethernet/oc-opt-term:lldp/oc-opt-term:neighbors/oc-opt-term:neighbor/oc-opt-term:state {
      deviate add {
	      sonic-ext:db-name "STATE_DB";
	      sonic-ext:table-name "NEIGHBOR_TABLE";
	      sonic-ext:key-transformer "neighbor_key_xfmr";
      }
    }

    deviation /oc-opt-term:terminal-device/oc-opt-term:logical-channels/oc-opt-term:channel/oc-opt-term:ethernet/oc-opt-term:lldp/oc-opt-term:neighbors/oc-opt-term:neighbor/oc-opt-term:state/oc-opt-term:port-description {
      deviate add {
	    sonic-ext:field-name "port-description";
      }
    }

    deviation /oc-opt-term:terminal-device/oc-opt-term:logical-channels/oc-opt-term:channel/oc-opt-term:ethernet/oc-opt-term:lldp/oc-opt-term:neighbors/oc-opt-term:neighbor/oc-opt-term:state/oc-opt-term:last-update {
	    deviate add {
		    sonic-ext:field-name "last-update";	  
	    }
    }

    deviation /oc-opt-term:terminal-device/oc-opt-term:logical-channels/oc-opt-term:channel/oc-opt-term:ethernet/oc-opt-term:lldp/oc-opt-term:neighbors/oc-opt-term:neighbor/oc-opt-term:config/oc-opt-term:id {
      deviate add {
	    sonic-ext:field-transformer "neighbor_field_xfmr";	  
      }
    }

    deviation /oc-opt-term:terminal-device/oc-opt-term:logical-channels/oc-opt-term:channel/oc-opt-term:ethernet/oc-opt-term:lldp/oc-opt-term:neighbors/oc-opt-term:neighbor/oc-opt-term:state/oc-opt-term:id {
      deviate add {
	    sonic-ext:field-transformer "neighbor_field_xfmr";	  
      }
    }

    deviation /oc-opt-term:terminal-device/oc-opt-term:logical-channels/oc-opt-term:channel/oc-opt-term:ethernet/oc-opt-term:lldp/oc-opt-term:neighbors/oc-opt-term:neighbor/oc-opt-term:state/oc-opt-term:port-id-type {
        deviate add {
	    sonic-ext:field-name "port-id-type";	  
      }
    }

    deviation /oc-opt-term:terminal-device/oc-opt-term:logical-channels/oc-opt-term:channel/oc-opt-term:ethernet/oc-opt-term:lldp/oc-opt-term:neighbors/oc-opt-term:neighbor/oc-opt-term:state/oc-opt-term:port-id {
      deviate add {
	    sonic-ext:field-name "port-id";	  
      }
    }

    deviation /oc-opt-term:terminal-device/oc-opt-term:logical-channels/oc-opt-term:channel/oc-opt-term:ethernet/oc-opt-term:lldp/oc-opt-term:neighbors/oc-opt-term:neighbor/oc-opt-term:state/oc-opt-term:chassis-id-type {
      deviate add {
	    sonic-ext:field-name "chassis-id-type";	  
      }
    }

    deviation /oc-opt-term:terminal-device/oc-opt-term:logical-channels/oc-opt-term:channel/oc-opt-term:ethernet/oc-opt-term:lldp/oc-opt-term:neighbors/oc-opt-term:neighbor/oc-opt-term:state/oc-opt-term:ttl {
      deviate add {
	    sonic-ext:field-name "ttl";	  
      }
    }

    deviation /oc-opt-term:terminal-device/oc-opt-term:logical-channels/oc-opt-term:channel/oc-opt-term:ethernet/oc-opt-term:lldp/oc-opt-term:neighbors/oc-opt-term:neighbor/oc-opt-term:state/oc-opt-term:age {
      deviate add {
	    sonic-ext:field-name "age";	  
      }
    }

    deviation /oc-opt-term:terminal-device/oc-opt-term:logical-channels/oc-opt-term:channel/oc-opt-term:ethernet/oc-opt-term:lldp/oc-opt-term:neighbors/oc-opt-term:neighbor/oc-opt-term:state/oc-opt-term:chassis-id {
      deviate add {
	    sonic-ext:field-name "chassis-id";	  
      }
    }

    deviation /oc-opt-term:terminal-device/oc-opt-term:logical-channels/oc-opt-term:channel/oc-opt-term:ethernet/oc-opt-term:lldp/oc-opt-term:neighbors/oc-opt-term:neighbor/oc-opt-term:state/oc-opt-term:management-address-type {
      deviate add {
	    sonic-ext:field-name "management-address-type";	  
      }
    }

    deviation /oc-opt-term:terminal-device/oc-opt-term:logical-channels/oc-opt-term:channel/oc-opt-term:ethernet/oc-opt-term:lldp/oc-opt-term:neighbors/oc-opt-term:neighbor/oc-opt-term:state/oc-opt-term:system-description {
      deviate add {
	    sonic-ext:field-name "system-description";	  
      }
    }

    deviation /oc-opt-term:terminal-device/oc-opt-term:logical-channels/oc-opt-term:channel/oc-opt-term:ethernet/oc-opt-term:lldp/oc-opt-term:neighbors/oc-opt-term:neighbor/oc-opt-term:state/oc-opt-term:management-address {
      deviate add {
	    sonic-ext:field-name "management-address";	  
      }
    }

    deviation /oc-opt-term:terminal-device/oc-opt-term:logical-channels/oc-opt-term:channel/oc-opt-term:ethernet/oc-opt-term:lldp/oc-opt-term:neighbors/oc-opt-term:neighbor/oc-opt-term:state/oc-opt-term:system-name {
      deviate add {
	    sonic-ext:field-name "system-name";	  
      }
    }

    deviation /oc-opt-term:terminal-device/oc-opt-term:logical-channels/oc-opt-term:channel/oc-opt-term:logical-channel-assignments {
      deviate add {
	      //sonic-ext:get-namespace "td_get_namespace_xfmr";		
      }
    }

    deviation /oc-opt-term:terminal-device/oc-opt-term:logical-channels/oc-opt-term:channel/oc-opt-term:logical-channel-assignments/oc-opt-term:assignment {
      deviate add {
	      sonic-ext:table-name "ASSIGNMENT";
	      sonic-ext:key-transformer "assignment_key_xfmr";
      }
    }

    deviation /oc-opt-term:terminal-device/oc-opt-term:logical-channels/oc-opt-term:channel/oc-opt-term:logical-channel-assignments/oc-opt-term:assignment/oc-opt-term:index {
      deviate add {
      }
    }

    deviation /oc-opt-term:terminal-device/oc-opt-term:logical-channels/oc-opt-term:channel/oc-opt-term:logical-channel-assignments/oc-opt-term:assignment/oc-opt-term:config {
      deviate add {
      }
    }

    deviation /oc-opt-term:terminal-device/oc-opt-term:logical-channels/oc-opt-term:channel/oc-opt-term:logical-channel-assignments/oc-opt-term:assignment/oc-opt-term:config/oc-opt-term:mapping {
      deviate add {
      }
    }

    deviation /oc-opt-term:terminal-device/oc-opt-term:logical-channels/oc-opt-term:channel/oc-opt-term:logical-channel-assignments/oc-opt-term:assignment/oc-opt-term:config/oc-opt-term:index {
      deviate add {
	    sonic-ext:field-transformer "assignment_field_xfmr";
      }
    }

    deviation /oc-opt-term:terminal-device/oc-opt-term:logical-channels/oc-opt-term:channel/oc-opt-term:logical-channel-assignments/oc-opt-term:assignment/oc-opt-term:config/oc-opt-term:description {
      deviate add {
      }
    }

    deviation /oc-opt-term:terminal-device/oc-opt-term:logical-channels/oc-opt-term:channel/oc-opt-term:logical-channel-assignments/oc-opt-term:assignment/oc-opt-term:config/oc-opt-term:assignment-type {
      deviate add {
      }
    }

    deviation /oc-opt-term:terminal-device/oc-opt-term:logical-channels/oc-opt-term:channel/oc-opt-term:logical-channel-assignments/oc-opt-term:assignment/oc-opt-term:config/oc-opt-term:logical-channel {
      deviate add {
      }
    }

    deviation /oc-opt-term:terminal-device/oc-opt-term:logical-channels/oc-opt-term:channel/oc-opt-term:logical-channel-assignments/oc-opt-term:assignment/oc-opt-term:config/oc-opt-term:optical-channel {
      deviate add {
      }
    }

    deviation /oc-opt-term:terminal-device/oc-opt-term:logical-channels/oc-opt-term:channel/oc-opt-term:logical-channel-assignments/oc-opt-term:assignment/oc-opt-term:config/oc-opt-term:allocation {
      deviate add {
      }
    }

    deviation /oc-opt-term:terminal-device/oc-opt-term:logical-channels/oc-opt-term:channel/oc-opt-term:logical-channel-assignments/oc-opt-term:assignment/oc-opt-term:config/oc-opt-term:tributary-slot-index {
      deviate add {
      }
    }

    deviation /oc-opt-term:terminal-device/oc-opt-term:logical-channels/oc-opt-term:channel/oc-opt-term:logical-channel-assignments/oc-opt-term:assignment/oc-opt-term:state {
      deviate add {
	      sonic-ext:db-name "STATE_DB";
	      sonic-ext:table-name "ASSIGNMENT_TABLE";
	      sonic-ext:key-transformer "assignment_key_xfmr";
      }
   }
    

    deviation /oc-opt-term:terminal-device/oc-opt-term:logical-channels/oc-opt-term:channel/oc-opt-term:logical-channel-assignments/oc-opt-term:assignment/oc-opt-term:state/oc-opt-term:mapping {
      deviate add {
      }
    }

    deviation /oc-opt-term:terminal-device/oc-opt-term:logical-channels/oc-opt-term:channel/oc-opt-term:logical-channel-assignments/oc-opt-term:assignment/oc-opt-term:state/oc-opt-term:index {
      deviate add {
	    sonic-ext:field-transformer "assignment_field_xfmr";
      }
    }

    deviation /oc-opt-term:terminal-device/oc-opt-term:logical-channels/oc-opt-term:channel/oc-opt-term:logical-channel-assignments/oc-opt-term:assignment/oc-opt-term:state/oc-opt-term:description {
      deviate add {
	    sonic-ext:field-name "description";
      }
    }

    deviation /oc-opt-term:terminal-device/oc-opt-term:logical-channels/oc-opt-term:channel/oc-opt-term:logical-channel-assignments/oc-opt-term:assignment/oc-opt-term:state/oc-opt-term:assignment-type {
      deviate add {
	    sonic-ext:field-name "assignment-type";
      }
    }

    deviation /oc-opt-term:terminal-device/oc-opt-term:logical-channels/oc-opt-term:channel/oc-opt-term:logical-channel-assignments/oc-opt-term:assignment/oc-opt-term:state/oc-opt-term:logical-channel {
      deviate add {
	    sonic-ext:field-transformer "ass_logical_field_xfmr";
      }
    }

    deviation /oc-opt-term:terminal-device/oc-opt-term:logical-channels/oc-opt-term:channel/oc-opt-term:logical-channel-assignments/oc-opt-term:assignment/oc-opt-term:state/oc-opt-term:optical-channel {
      deviate add {
	    sonic-ext:field-name "optical-channel";
      }
    }

    deviation /oc-opt-term:terminal-device/oc-opt-term:logical-channels/oc-opt-term:channel/oc-opt-term:logical-channel-assignments/oc-opt-term:assignment/oc-opt-term:state/oc-opt-term:allocation {
      deviate add {
	    sonic-ext:field-name "allocation";
      }
    }

    deviation /oc-opt-term:terminal-device/oc-opt-term:logical-channels/oc-opt-term:channel/oc-opt-term:logical-channel-assignments/oc-opt-term:assignment/oc-opt-term:state/oc-opt-term:tributary-slot-index {
      deviate add {
	    sonic-ext:field-name "tributary-slot-index";
      }
    }

    deviation /oc-opt-term:terminal-device/oc-opt-term:logical-channels/oc-opt-term:channel/oc-opt-term:otn {
      deviate add {
	      sonic-ext:table-name "OTN";
	      sonic-ext:key-transformer "logical_channel_key_xfmr";
      }
    }

    deviation /oc-opt-term:terminal-device/oc-opt-term:logical-channels/oc-opt-term:channel/oc-opt-term:otn/oc-opt-term:state {
      deviate add {
	      sonic-ext:table-name "OTN_TABLE";
	      sonic-ext:db-name "STATE_DB";
	      sonic-ext:key-transformer "logical_channel_key_xfmr";
      }
    }

    deviation /oc-opt-term:terminal-device/oc-opt-term:logical-channels/oc-opt-term:channel/oc-opt-term:otn/oc-opt-term:state/oc-opt-term:fec-corrected-bytes {
      deviate add {
	    sonic-ext:table-name "OTN";
	    sonic-ext:db-name "COUNTERS_DB";
	    sonic-ext:key-transformer "otn_counter_key_xfmr";
	    sonic-ext:field-name "fec-corrected-bytes";
      }
    }

    deviation /oc-opt-term:terminal-device/oc-opt-term:logical-channels/oc-opt-term:channel/oc-opt-term:otn/oc-opt-term:state/oc-opt-term:fec-corrected-bits {
      deviate add {
	    sonic-ext:table-name "OTN";
	    sonic-ext:db-name "COUNTERS_DB";
	    sonic-ext:key-transformer "otn_counter_key_xfmr";
	    sonic-ext:field-name "fec-corrected-bits";	  
      }
    }

    deviation /oc-opt-term:terminal-device/oc-opt-term:logical-channels/oc-opt-term:channel/oc-opt-term:otn/oc-opt-term:state/oc-opt-term:pre-fec-ber {
      deviate add {
	    sonic-ext:table-name "OTN";
	    sonic-ext:db-name "COUNTERS_DB";
	    sonic-ext:key-transformer "otn_pre_fec_ber_counter_key_xfmr";
      }
    }

    deviation /oc-opt-term:terminal-device/oc-opt-term:logical-channels/oc-opt-term:channel/oc-opt-term:otn/oc-opt-term:state/oc-opt-term:pre-fec-ber/oc-opt-term:min {
      deviate add {
	    sonic-ext:field-name "min";
      }
    }

    deviation /oc-opt-term:terminal-device/oc-opt-term:logical-channels/oc-opt-term:channel/oc-opt-term:otn/oc-opt-term:state/oc-opt-term:pre-fec-ber/oc-opt-term:max {
      deviate add {
	    sonic-ext:field-name "max";	  
      }
    }

    deviation /oc-opt-term:terminal-device/oc-opt-term:logical-channels/oc-opt-term:channel/oc-opt-term:otn/oc-opt-term:state/oc-opt-term:pre-fec-ber/oc-opt-term:interval {
      deviate add {
	    sonic-ext:field-name "interval";	  
      }
    }

    deviation /oc-opt-term:terminal-device/oc-opt-term:logical-channels/oc-opt-term:channel/oc-opt-term:otn/oc-opt-term:state/oc-opt-term:pre-fec-ber/oc-opt-term:min-time {
      deviate add {
	    sonic-ext:field-name "min-time";	  
      }
    }

    deviation /oc-opt-term:terminal-device/oc-opt-term:logical-channels/oc-opt-term:channel/oc-opt-term:otn/oc-opt-term:state/oc-opt-term:pre-fec-ber/oc-opt-term:max-time {
      deviate add {
	    sonic-ext:field-name "max-time";	  
      }
    }

    deviation /oc-opt-term:terminal-device/oc-opt-term:logical-channels/oc-opt-term:channel/oc-opt-term:otn/oc-opt-term:state/oc-opt-term:pre-fec-ber/oc-opt-term:instant {
      deviate add {
	    sonic-ext:field-name "instant";	  
      }
    }

    deviation /oc-opt-term:terminal-device/oc-opt-term:logical-channels/oc-opt-term:channel/oc-opt-term:otn/oc-opt-term:state/oc-opt-term:pre-fec-ber/oc-opt-term:avg {
      deviate add {
	    sonic-ext:field-name "avg";	  
      }
    }

    deviation /oc-opt-term:terminal-device/oc-opt-term:logical-channels/oc-opt-term:channel/oc-opt-term:otn/oc-opt-term:state/oc-opt-term:code-violations {
      deviate add {
	    sonic-ext:table-name "OTN";
	    sonic-ext:db-name "COUNTERS_DB";
	    sonic-ext:key-transformer "otn_counter_key_xfmr";
	    sonic-ext:field-name "code-violations";		  
      }
    }

    deviation /oc-opt-term:terminal-device/oc-opt-term:logical-channels/oc-opt-term:channel/oc-opt-term:otn/oc-opt-term:state/oc-opt-term:errored-blocks {
      deviate add {
	    sonic-ext:table-name "OTN";
	    sonic-ext:db-name "COUNTERS_DB";
	    sonic-ext:key-transformer "otn_counter_key_xfmr";
	    sonic-ext:field-name "errored-blocks";	
      }
    }

    deviation /oc-opt-term:terminal-device/oc-opt-term:logical-channels/oc-opt-term:channel/oc-opt-term:otn/oc-opt-term:state/oc-opt-term:tributary-slot-granularity {
      deviate add {
      }
    }

    deviation /oc-opt-term:terminal-device/oc-opt-term:logical-channels/oc-opt-term:channel/oc-opt-term:otn/oc-opt-term:state/oc-opt-term:fec-uncorrectable-blocks {
      deviate add {
	    sonic-ext:table-name "OTN";
	    sonic-ext:db-name "COUNTERS_DB";
	    sonic-ext:key-transformer "otn_counter_key_xfmr";
	    sonic-ext:field-name "fec-uncorrectable-blocks";		    
      }
    }
    deviation /oc-opt-term:terminal-device/oc-opt-term:logical-channels/oc-opt-term:channel/oc-opt-term:otn/oc-opt-term:state/oc-opt-term:tti-msg-auto {
      deviate add {
	    sonic-ext:field-name "tti-msg-auto";
      }
    }

    deviation /oc-opt-term:terminal-device/oc-opt-term:logical-channels/oc-opt-term:channel/oc-opt-term:otn/oc-opt-term:state/oc-opt-term:esnr {
      deviate add {
	      sonic-ext:table-name "OTN";
	      sonic-ext:db-name "COUNTERS_DB";
	      sonic-ext:key-transformer "otn_esnr_counter_key_xfmr";
      }
    }

    deviation /oc-opt-term:terminal-device/oc-opt-term:logical-channels/oc-opt-term:channel/oc-opt-term:otn/oc-opt-term:state/oc-opt-term:esnr/oc-opt-term:max-time {
      deviate add {
        sonic-ext:field-name "max-time";	  
      }
    }

    deviation /oc-opt-term:terminal-device/oc-opt-term:logical-channels/oc-opt-term:channel/oc-opt-term:otn/oc-opt-term:state/oc-opt-term:esnr/oc-opt-term:instant {
      deviate add {
        sonic-ext:field-name "instant";	  
      }
    }

    deviation /oc-opt-term:terminal-device/oc-opt-term:logical-channels/oc-opt-term:channel/oc-opt-term:otn/oc-opt-term:state/oc-opt-term:esnr/oc-opt-term:avg {
      deviate add {
        sonic-ext:field-name "avg";	  
      }
    }

    deviation /oc-opt-term:terminal-device/oc-opt-term:logical-channels/oc-opt-term:channel/oc-opt-term:otn/oc-opt-term:state/oc-opt-term:esnr/oc-opt-term:min {
      deviate add {
	    sonic-ext:field-name "min";
      }
    }

    deviation /oc-opt-term:terminal-device/oc-opt-term:logical-channels/oc-opt-term:channel/oc-opt-term:otn/oc-opt-term:state/oc-opt-term:esnr/oc-opt-term:max {
      deviate add {
        sonic-ext:field-name "max";
      }
    }

    deviation /oc-opt-term:terminal-device/oc-opt-term:logical-channels/oc-opt-term:channel/oc-opt-term:otn/oc-opt-term:state/oc-opt-term:esnr/oc-opt-term:interval {
      deviate add {
        sonic-ext:field-name "interval";
      }
    }

    deviation /oc-opt-term:terminal-device/oc-opt-term:logical-channels/oc-opt-term:channel/oc-opt-term:otn/oc-opt-term:state/oc-opt-term:esnr/oc-opt-term:min-time {
      deviate add {
        sonic-ext:field-name "min-time";
      }
    }

    deviation /oc-opt-term:terminal-device/oc-opt-term:logical-channels/oc-opt-term:channel/oc-opt-term:otn/oc-opt-term:state/oc-opt-term:fec-uncorrectable-words {
      deviate add {
	    sonic-ext:table-name "OTN";
	    sonic-ext:db-name "COUNTERS_DB";
	    sonic-ext:key-transformer "otn_counter_key_xfmr";
	    sonic-ext:field-name "fec-uncorrectable-words";
      }
    }

    deviation /oc-opt-term:terminal-device/oc-opt-term:logical-channels/oc-opt-term:channel/oc-opt-term:otn/oc-opt-term:state/oc-opt-term:tti-msg-expected {
      deviate add {
	    sonic-ext:field-name "tti-msg-expected";	  
      } 
    }

    deviation /oc-opt-term:terminal-device/oc-opt-term:logical-channels/oc-opt-term:channel/oc-opt-term:otn/oc-opt-term:state/oc-opt-term:tti-msg-recv {
      deviate add {
	    sonic-ext:field-name "tti-msg-recv";
      }
    }

    deviation /oc-opt-term:terminal-device/oc-opt-term:logical-channels/oc-opt-term:channel/oc-opt-term:otn/oc-opt-term:state/oc-opt-term:errored-seconds {
      deviate add {
	    sonic-ext:table-name "OTN";
	    sonic-ext:db-name "COUNTERS_DB";
	    sonic-ext:key-transformer "otn_counter_key_xfmr";
	    sonic-ext:field-name "errored-seconds";
      }
    }

    deviation /oc-opt-term:terminal-device/oc-opt-term:logical-channels/oc-opt-term:channel/oc-opt-term:otn/oc-opt-term:state/oc-opt-term:tti-msg-transmit {
      deviate add {
	    sonic-ext:field-name "tti-msg-transmit";
      }
    }

    deviation /oc-opt-term:terminal-device/oc-opt-term:logical-channels/oc-opt-term:channel/oc-opt-term:otn/oc-opt-term:state/oc-opt-term:severely-errored-seconds {
      deviate add {
	    sonic-ext:table-name "OTN";
	    sonic-ext:db-name "COUNTERS_DB";
	    sonic-ext:key-transformer "otn_counter_key_xfmr";
	    sonic-ext:field-name "severely-errored-seconds";	    
      }
    }

    deviation /oc-opt-term:terminal-device/oc-opt-term:logical-channels/oc-opt-term:channel/oc-opt-term:otn/oc-opt-term:state/oc-opt-term:rdi-msg {
      deviate add {
	    sonic-ext:field-name "rdi-msg";
      }
    }
    deviation /oc-opt-term:terminal-device/oc-opt-term:logical-channels/oc-opt-term:channel/oc-opt-term:otn/oc-opt-term:state/oc-opt-term:unavailable-seconds {
      deviate add {
	    sonic-ext:table-name "OTN";
	    sonic-ext:db-name "COUNTERS_DB";
	    sonic-ext:key-transformer "otn_counter_key_xfmr";
	    sonic-ext:field-name "unavailable-seconds";	  
      }
    }

    deviation /oc-opt-term:terminal-device/oc-opt-term:logical-channels/oc-opt-term:channel/oc-opt-term:otn/oc-opt-term:state/oc-opt-term:post-fec-ber {
      deviate add {
	    sonic-ext:db-name "COUNTERS_DB";
	    sonic-ext:table-name "OTN";
	    sonic-ext:key-transformer "otn_post_fec_ber_counter_key_xfmr";
      }
    }

    deviation /oc-opt-term:terminal-device/oc-opt-term:logical-channels/oc-opt-term:channel/oc-opt-term:otn/oc-opt-term:state/oc-opt-term:post-fec-ber/oc-opt-term:interval {
      deviate add {
	    sonic-ext:field-name "interval";
      }
    }

    deviation /oc-opt-term:terminal-device/oc-opt-term:logical-channels/oc-opt-term:channel/oc-opt-term:otn/oc-opt-term:state/oc-opt-term:post-fec-ber/oc-opt-term:min-time {
      deviate add {
	    sonic-ext:field-name "min-time";	  
      }
    }

    deviation /oc-opt-term:terminal-device/oc-opt-term:logical-channels/oc-opt-term:channel/oc-opt-term:otn/oc-opt-term:state/oc-opt-term:post-fec-ber/oc-opt-term:max-time {
      deviate add {
	    sonic-ext:field-name "max-time";	  
      }
    }

    deviation /oc-opt-term:terminal-device/oc-opt-term:logical-channels/oc-opt-term:channel/oc-opt-term:otn/oc-opt-term:state/oc-opt-term:post-fec-ber/oc-opt-term:instant {
      deviate add {
	    sonic-ext:field-name "instant";
      }
    }

    deviation /oc-opt-term:terminal-device/oc-opt-term:logical-channels/oc-opt-term:channel/oc-opt-term:otn/oc-opt-term:state/oc-opt-term:post-fec-ber/oc-opt-term:avg {
      deviate add {
	    sonic-ext:field-name "avg";	  
      }
    }

    deviation /oc-opt-term:terminal-device/oc-opt-term:logical-channels/oc-opt-term:channel/oc-opt-term:otn/oc-opt-term:state/oc-opt-term:post-fec-ber/oc-opt-term:min {
      deviate add {
	    sonic-ext:field-name "min";	  
      }
    }

    deviation /oc-opt-term:terminal-device/oc-opt-term:logical-channels/oc-opt-term:channel/oc-opt-term:otn/oc-opt-term:state/oc-opt-term:post-fec-ber/oc-opt-term:max {
      deviate add {
	    sonic-ext:field-name "max";	  
      }
    }

    deviation /oc-opt-term:terminal-device/oc-opt-term:logical-channels/oc-opt-term:channel/oc-opt-term:otn/oc-opt-term:state/oc-opt-term:q-value {
      deviate add {
	      sonic-ext:db-name "COUNTERS_DB";
	      sonic-ext:table-name "OTN";
	      sonic-ext:key-transformer "otn_qvalue_counter_key_xfmr";	  
      }
    }

    deviation /oc-opt-term:terminal-device/oc-opt-term:logical-channels/oc-opt-term:channel/oc-opt-term:otn/oc-opt-term:state/oc-opt-term:q-value/oc-opt-term:avg {
      deviate add {
	    sonic-ext:field-name "avg";
      }
    }

    deviation /oc-opt-term:terminal-device/oc-opt-term:logical-channels/oc-opt-term:channel/oc-opt-term:otn/oc-opt-term:state/oc-opt-term:q-value/oc-opt-term:min {
      deviate add {
	    sonic-ext:field-name "min";	  
      }
    }

    deviation /oc-opt-term:terminal-device/oc-opt-term:logical-channels/oc-opt-term:channel/oc-opt-term:otn/oc-opt-term:state/oc-opt-term:q-value/oc-opt-term:max {
      deviate add {
	    sonic-ext:field-name "max";	  
      }
    }

    deviation /oc-opt-term:terminal-device/oc-opt-term:logical-channels/oc-opt-term:channel/oc-opt-term:otn/oc-opt-term:state/oc-opt-term:q-value/oc-opt-term:interval {
      deviate add {
	    sonic-ext:field-name "interval";	  
      }
    }

    deviation /oc-opt-term:terminal-device/oc-opt-term:logical-channels/oc-opt-term:channel/oc-opt-term:otn/oc-opt-term:state/oc-opt-term:q-value/oc-opt-term:min-time {
      deviate add {
	    sonic-ext:field-name "min-time";	  
      }
    }

    deviation /oc-opt-term:terminal-device/oc-opt-term:logical-channels/oc-opt-term:channel/oc-opt-term:otn/oc-opt-term:state/oc-opt-term:q-value/oc-opt-term:max-time {
      deviate add {
	    sonic-ext:field-name "max-time";	  
      }
    }

    deviation /oc-opt-term:terminal-device/oc-opt-term:logical-channels/oc-opt-term:channel/oc-opt-term:otn/oc-opt-term:state/oc-opt-term:q-value/oc-opt-term:instant {
      deviate add {
	    sonic-ext:field-name "instant";	  
      }
    }

    deviation /oc-opt-term:terminal-device/oc-opt-term:logical-channels/oc-opt-term:channel/oc-opt-term:otn/oc-opt-term:state/oc-opt-term:background-block-errors {
      deviate add {
	      sonic-ext:table-name "OTN";
	      sonic-ext:db-name "COUNTERS_DB";
	      sonic-ext:key-transformer "otn_counter_key_xfmr";
	      sonic-ext:field-name "background-block-errors";	  
      }
    }

    deviation /oc-opt-term:terminal-device/oc-opt-term:logical-channels/oc-opt-term:-channel/oc-opt-term:otn/oc-opt-term:config {
      deviate add {
      }
    }

    deviation /oc-opt-term:terminal-device/oc-opt-term:logical-channels/oc-opt-term:channel/oc-opt-term:otn/oc-opt-term:config/oc-opt-term:tti-msg-expected {
      deviate add {
	    sonic-ext:field-name "tti-msg-expected";
      }
    }

    deviation /oc-opt-term:terminal-device/oc-opt-term:logical-channels/oc-opt-term:channel/oc-opt-term:otn/oc-opt-term:config/oc-opt-term:tti-msg-auto {
      deviate add {
	    sonic-ext:field-name "tti-msg-auto";
      }
    }

    deviation /oc-opt-term:terminal-device/oc-opt-term:logical-channels/oc-opt-term:channel/oc-opt-term:otn/oc-opt-term:config/oc-opt-term:tributary-slot-granularity {
      deviate add {
      }
    }

    deviation /oc-opt-term:terminal-device/oc-opt-term:logical-channels/oc-opt-term:channel/oc-opt-term:otn/oc-opt-term:config/oc-opt-term:tti-msg-transmit {
      deviate add {
	    sonic-ext:field-name "tti-msg-transmit";
      }
    }

    deviation /oc-opt-term:terminal-device/oc-opt-term:operational-modes {
      deviate add {
	      sonic-ext:db-name "STATE_DB";
	      sonic-ext:table-name "MODE_TABLE";	  
	      sonic-ext:get-namespace "td_get_namespace_xfmr";		
      }
    }

    deviation /oc-opt-term:terminal-device/oc-opt-term:operational-modes/oc-opt-term:mode {
      deviate add {
        sonic-ext:key-transformer "mode_key_xfmr";	 
      }
    }

    deviation /oc-opt-term:terminal-device/oc-opt-term:operational-modes/oc-opt-term:mode/oc-opt-term:config {
      deviate add {
      }
    }

    deviation /oc-opt-term:terminal-device/oc-opt-term:operational-modes/oc-opt-term:mode/oc-opt-term:state {
      deviate add {
	      sonic-ext:table-name "MODE_TABLE";	  
	      sonic-ext:key-transformer "mode_key_xfmr";	 
      }
    }

    deviation /oc-opt-term:terminal-device/oc-opt-term:operational-modes/oc-opt-term:mode/oc-opt-term:state/oc-opt-term:vendor-id {
      deviate add {
	    sonic-ext:field-name "vendor-id";
      }
    }

    deviation /oc-opt-term:terminal-device/oc-opt-term:operational-modes/oc-opt-term:mode/oc-opt-term:config/oc-opt-term:mode-id {
      deviate add {
	    sonic-ext:field-transformer "mode_field_xfmr";
      }
    }

    deviation /oc-opt-term:terminal-device/oc-opt-term:operational-modes/oc-opt-term:mode/oc-opt-term:state/oc-opt-term:mode-id {
      deviate add {
	    sonic-ext:field-transformer "mode_field_xfmr";
      }
    }

    deviation /oc-opt-term:terminal-device/oc-opt-term:operational-modes/oc-opt-term:mode/oc-opt-term:state/oc-opt-term:description {
      deviate add {
	    sonic-ext:field-name "description";
      }
    }

    deviation /oc-opt-term:terminal-device/oc-opt-term:operational-modes/oc-opt-term:mode/oc-opt-term:mode-id {
      deviate add {
      }
    }

}
