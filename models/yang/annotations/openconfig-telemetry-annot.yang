module openconfig-telemetry-annot {

        yang-version "1";

        namespace "http://openconfig.net/yang/annotation/oc-telemetry-annot";
        prefix "oc-telemetry-annot";

        import sonic-extensions { prefix sonic-ext; }
        import openconfig-telemetry { prefix oc-telemetry; }

        deviation /oc-telemetry:telemetry-system {
                deviate add {
                        sonic-ext:post-transformer "telemetry_client_sync_post_xfmr";
                        sonic-ext:get-namespace "telemetry_get_namespace_xfmr";
                }
        }


        deviation /oc-telemetry:telemetry-system/oc-telemetry:sensor-groups {
                deviate add {
                        sonic-ext:table-name "SENSOR_GROUP";
                }
        }

        deviation /oc-telemetry:telemetry-system/oc-telemetry:sensor-groups/oc-telemetry:sensor-group {
                deviate add {
                        sonic-ext:key-transformer "telemetry_sensor_group_id_key_xfmr";
                        sonic-ext:get-namespace "telemetry_get_namespace_xfmr";
                }
        }

        deviation  /oc-telemetry:telemetry-system/oc-telemetry:sensor-groups/oc-telemetry:sensor-group/oc-telemetry:config/oc-telemetry:sensor-group-id {
                deviate add {
                        sonic-ext:field-transformer "telemetry_sensor_group_id_field_xfmr";
                }
        }

        deviation  /oc-telemetry:telemetry-system/oc-telemetry:sensor-groups/oc-telemetry:sensor-group/oc-telemetry:sensor-paths{
                deviate add {
                }
        }

        deviation /oc-telemetry:telemetry-system/oc-telemetry:sensor-groups/oc-telemetry:sensor-group/oc-telemetry:sensor-paths/oc-telemetry:sensor-path {
	    deviate add {
			sonic-ext:key-transformer "telemetry_sensor_path_key_xfmr";
	     }
        }

        deviation  /oc-telemetry:telemetry-system/oc-telemetry:sensor-groups/oc-telemetry:sensor-group/oc-telemetry:sensor-paths/oc-telemetry:sensor-path/oc-telemetry:config/oc-telemetry:path {
                deviate add {
                        sonic-ext:field-name "sensor-paths";
                }
        }

	deviation /oc-telemetry:telemetry-system/oc-telemetry:destination-groups {
		deviate add {
			sonic-ext:table-name "DESTINATION_GROUP";
			sonic-ext:get-namespace "telemetry_get_namespace_xfmr";
		}
	}

	deviation /oc-telemetry:telemetry-system/oc-telemetry:destination-groups/oc-telemetry:destination-group {
		deviate add {
			sonic-ext:key-transformer "telemetry_group_id_key_xfmr";
			sonic-ext:get-namespace "telemetry_get_namespace_xfmr";
		}
	}

	deviation /oc-telemetry:telemetry-system/oc-telemetry:destination-groups/oc-telemetry:destination-group/oc-telemetry:config {
		deviate add {
		}
	}

	deviation /oc-telemetry:telemetry-system/oc-telemetry:destination-groups/oc-telemetry:destination-group/oc-telemetry:config/oc-telemetry:group-id {
		deviate add {
			sonic-ext:field-transformer "telemetry_group_id_field_xfmr";
		}
	}

	deviation /oc-telemetry:telemetry-system/oc-telemetry:destination-groups/oc-telemetry:destination-group/oc-telemetry:destinations {
		deviate add {
			sonic-ext:table-name "DESTINATION";
			sonic-ext:get-namespace "telemetry_get_namespace_xfmr";
		}
	}

	deviation /oc-telemetry:telemetry-system/oc-telemetry:destination-groups/oc-telemetry:destination-group/oc-telemetry:destinations/oc-telemetry:destination {
		deviate add {
			sonic-ext:key-transformer "telemetry_destination_key_xfmr";
			sonic-ext:get-namespace "telemetry_get_namespace_xfmr";
		}
	}

	deviation /oc-telemetry:telemetry-system/oc-telemetry:destination-groups/oc-telemetry:destination-group/oc-telemetry:destinations/oc-telemetry:destination/oc-telemetry:destination-address {
		deviate add {
		}
	}

	deviation /oc-telemetry:telemetry-system/oc-telemetry:destination-groups/oc-telemetry:destination-group/oc-telemetry:destinations/oc-telemetry:destination/oc-telemetry:destination-port {
		deviate add {
		}
	}

	deviation /oc-telemetry:telemetry-system/oc-telemetry:destination-groups/oc-telemetry:destination-group/oc-telemetry:destinations/oc-telemetry:destination/oc-telemetry:config {
		deviate add {
		}
	}

	deviation /oc-telemetry:telemetry-system/oc-telemetry:destination-groups/oc-telemetry:destination-group/oc-telemetry:destinations/oc-telemetry:destination/oc-telemetry:config/oc-telemetry:destination-address {
		deviate add {
			sonic-ext:field-transformer "telemetry_destination_address_field_xfmr";
		}
	}

	deviation /oc-telemetry:telemetry-system/oc-telemetry:destination-groups/oc-telemetry:destination-group/oc-telemetry:destinations/oc-telemetry:destination/oc-telemetry:config/oc-telemetry:destination-port {
		deviate add {
			sonic-ext:field-transformer "telemetry_destination_port_field_xfmr";
		}
	}

	deviation /oc-telemetry:telemetry-system/oc-telemetry:destination-groups/oc-telemetry:destination-group/oc-telemetry:group-id {
		deviate add {
		}
	}

        deviation /oc-telemetry:telemetry-system/oc-telemetry:subscriptions {
		deviate add {
			sonic-ext:get-namespace "telemetry_get_namespace_xfmr";
		}
	}

	deviation /oc-telemetry:telemetry-system/oc-telemetry:subscriptions/oc-telemetry:persistent-subscriptions {
		deviate add {
			sonic-ext:table-name "PERSISTENT_SUBSCRIPTION";
		}
	}

	deviation /oc-telemetry:telemetry-system/oc-telemetry:subscriptions/oc-telemetry:persistent-subscriptions/oc-telemetry:persistent-subscription {
		deviate add {
			sonic-ext:key-transformer "telemetry_persistent_subscription_key_xfmr";
			sonic-ext:get-namespace "telemetry_get_namespace_xfmr";
		}
	}

	deviation /oc-telemetry:telemetry-system/oc-telemetry:subscriptions/oc-telemetry:persistent-subscriptions/oc-telemetry:persistent-subscription/oc-telemetry:config {
		deviate add {
		}
	}

	deviation /oc-telemetry:telemetry-system/oc-telemetry:subscriptions/oc-telemetry:persistent-subscriptions/oc-telemetry:persistent-subscription/oc-telemetry:config/oc-telemetry:name {
		deviate add {
			sonic-ext:field-transformer "telemetry_persistent_subscription_field_xfmr";
		}
	}

	deviation /oc-telemetry:telemetry-system/oc-telemetry:subscriptions/oc-telemetry:persistent-subscriptions/oc-telemetry:persistent-subscription/oc-telemetry:config/oc-telemetry:local-source-address {
		deviate add {
		}
	}

	deviation /oc-telemetry:telemetry-system/oc-telemetry:subscriptions/oc-telemetry:persistent-subscriptions/oc-telemetry:persistent-subscription/oc-telemetry:config/oc-telemetry:originated-qos-marking {
		deviate add {
		}
	}

	deviation /oc-telemetry:telemetry-system/oc-telemetry:subscriptions/oc-telemetry:persistent-subscriptions/oc-telemetry:persistent-subscription/oc-telemetry:config/oc-telemetry:protocol {
		deviate add {
			sonic-ext:field-name "protocol"; 
		}
	}

	deviation /oc-telemetry:telemetry-system/oc-telemetry:subscriptions/oc-telemetry:persistent-subscriptions/oc-telemetry:persistent-subscription/oc-telemetry:config/oc-telemetry:encoding {
		deviate add {
			sonic-ext:field-name "encoding";
		}
	}

	deviation /oc-telemetry:telemetry-system/oc-telemetry:subscriptions/oc-telemetry:persistent-subscriptions/oc-telemetry:persistent-subscription/oc-telemetry:sensor-profiles {
		deviate add {
			sonic-ext:table-name "SENSOR_PROFILE";
		}
	}

	deviation /oc-telemetry:telemetry-system/oc-telemetry:subscriptions/oc-telemetry:persistent-subscriptions/oc-telemetry:persistent-subscription/oc-telemetry:sensor-profiles/oc-telemetry:sensor-profile {
		deviate add {
			sonic-ext:key-transformer "telemetry_sensor_profile_key_xfmr";
			sonic-ext:get-namespace "telemetry_get_namespace_xfmr";
		}
	}

	deviation /oc-telemetry:telemetry-system/oc-telemetry:subscriptions/oc-telemetry:persistent-subscriptions/oc-telemetry:persistent-subscription/oc-telemetry:sensor-profiles/oc-telemetry:sensor-profile/oc-telemetry:sensor-group {
		deviate add {
		}
	}

	deviation /oc-telemetry:telemetry-system/oc-telemetry:subscriptions/oc-telemetry:persistent-subscriptions/oc-telemetry:persistent-subscription/oc-telemetry:sensor-profiles/oc-telemetry:sensor-profile/oc-telemetry:config {
		deviate add {
		}
	}

	deviation /oc-telemetry:telemetry-system/oc-telemetry:subscriptions/oc-telemetry:persistent-subscriptions/oc-telemetry:persistent-subscription/oc-telemetry:sensor-profiles/oc-telemetry:sensor-profile/oc-telemetry:config/oc-telemetry:suppress-redundant {
		deviate add {
		}
	}

	deviation /oc-telemetry:telemetry-system/oc-telemetry:subscriptions/oc-telemetry:persistent-subscriptions/oc-telemetry:persistent-subscription/oc-telemetry:sensor-profiles/oc-telemetry:sensor-profile/oc-telemetry:config/oc-telemetry:sensor-group {
		deviate add {
			sonic-ext:field-transformer "telemetry_sensor_profile_field_xfmr";
		}
	}

	deviation /oc-telemetry:telemetry-system/oc-telemetry:subscriptions/oc-telemetry:persistent-subscriptions/oc-telemetry:persistent-subscription/oc-telemetry:sensor-profiles/oc-telemetry:sensor-profile/oc-telemetry:config/oc-telemetry:sample-interval {
		deviate add {
			sonic-ext:field-name "sample-interval";
		}
	}

	deviation /oc-telemetry:telemetry-system/oc-telemetry:subscriptions/oc-telemetry:persistent-subscriptions/oc-telemetry:persistent-subscription/oc-telemetry:sensor-profiles/oc-telemetry:sensor-profile/oc-telemetry:config/oc-telemetry:heartbeat-interval {
		deviate add {
			sonic-ext:field-name "heartbeat-interval";
		}
	}

	deviation /oc-telemetry:telemetry-system/oc-telemetry:subscriptions/oc-telemetry:persistent-subscriptions/oc-telemetry:persistent-subscription/oc-telemetry:destination-groups {
		deviate add {
			sonic-ext:table-name "SUBSCRIPTION_DESTINATION_GROUP"; 
		}
	}

	deviation /oc-telemetry:telemetry-system/oc-telemetry:subscriptions/oc-telemetry:persistent-subscriptions/oc-telemetry:persistent-subscription/oc-telemetry:destination-groups/oc-telemetry:destination-group {
		deviate add {
			sonic-ext:key-transformer "telemetry_sub_dest_group_id_key_xfmr"; 
			sonic-ext:get-namespace "telemetry_get_namespace_xfmr";
		}
	}

	deviation /oc-telemetry:telemetry-system/oc-telemetry:subscriptions/oc-telemetry:persistent-subscriptions/oc-telemetry:persistent-subscription/oc-telemetry:destination-groups/oc-telemetry:destination-group/oc-telemetry:group-id {
		deviate add {
		}
	}

	deviation /oc-telemetry:telemetry-system/oc-telemetry:subscriptions/oc-telemetry:persistent-subscriptions/oc-telemetry:persistent-subscription/oc-telemetry:destination-groups/oc-telemetry:destination-group/oc-telemetry:config {
		deviate add {
		}
	}

	deviation /oc-telemetry:telemetry-system/oc-telemetry:subscriptions/oc-telemetry:persistent-subscriptions/oc-telemetry:persistent-subscription/oc-telemetry:destination-groups/oc-telemetry:destination-group/oc-telemetry:config/oc-telemetry:group-id {
		deviate add {
			sonic-ext:field-transformer "telemetry_sub_dest_group_id_field_xfmr";
		}
	}

	deviation /oc-telemetry:telemetry-system/oc-telemetry:subscriptions/oc-telemetry:persistent-subscriptions/oc-telemetry:persistent-subscription/oc-telemetry:name {
		deviate add {
		}
	}
}
