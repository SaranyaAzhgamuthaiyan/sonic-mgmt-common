module openconfig-optical-amplifier-annot {

    yang-version "1";

    namespace "http://openconfig.net/yang/annotation/oc-opt-amp-annot";
    prefix "oc-opt-amp-annot";

    import sonic-extensions { prefix sonic-ext; }
    import openconfig-optical-amplifier { prefix oc-opt-amp; }
    import com-oplink-amplifier-ext { prefix com-oplink-amplifier-ext; }

    deviation /oc-opt-amp:optical-amplifier {
      deviate add {
        sonic-ext:subscribe-on-change "enable";
        sonic-ext:get-namespace "oa_name_get_namespace_xfmr";
      }
    }

    deviation /oc-opt-amp:optical-amplifier/oc-opt-amp:amplifiers {
      deviate add {
        sonic-ext:table-name "AMPLIFIER";
      }
    }

    deviation /oc-opt-amp:optical-amplifier/oc-opt-amp:amplifiers/oc-opt-amp:amplifier {
      deviate add {
        sonic-ext:key-transformer "oa_name_key_xfmr";
      }
    }

    deviation /oc-opt-amp:optical-amplifier/oc-opt-amp:amplifiers/oc-opt-amp:amplifier/oc-opt-amp:config {
      deviate add {
      }
    }

    deviation /oc-opt-amp:optical-amplifier/oc-opt-amp:amplifiers/oc-opt-amp:amplifier/oc-opt-amp:config/oc-opt-amp:target-gain-tilt {
      deviate add {
        sonic-ext:field-name "target-gain-tilt";
      }
    }

    deviation /oc-opt-amp:optical-amplifier/oc-opt-amp:amplifiers/oc-opt-amp:amplifier/oc-opt-amp:config/oc-opt-amp:min-gain {
      deviate add {
        sonic-ext:field-name "min-gain";
      }
    }

    deviation /oc-opt-amp:optical-amplifier/oc-opt-amp:amplifiers/oc-opt-amp:amplifier/oc-opt-amp:config/oc-opt-amp:max-gain {
      deviate add {
        sonic-ext:field-name "max-gain";
      }
    }

    deviation /oc-opt-amp:optical-amplifier/oc-opt-amp:amplifiers/oc-opt-amp:amplifier/oc-opt-amp:config/oc-opt-amp:max-output-power {
      deviate add {
        sonic-ext:field-name "max-output-power";
      }
    }

    deviation /oc-opt-amp:optical-amplifier/oc-opt-amp:amplifiers/oc-opt-amp:amplifier/oc-opt-amp:config/oc-opt-amp:target-output-power {
      deviate add {
        sonic-ext:field-name "target-output-power";
      }
    }

    deviation /oc-opt-amp:optical-amplifier/oc-opt-amp:amplifiers/oc-opt-amp:amplifier/oc-opt-amp:config/oc-opt-amp:amp-mode {
      deviate add {
        sonic-ext:field-name "amp-mode";
      }
    }

    deviation /oc-opt-amp:optical-amplifier/oc-opt-amp:amplifiers/oc-opt-amp:amplifier/oc-opt-amp:config/oc-opt-amp:target-gain {
      deviate add {
        sonic-ext:field-name "target-gain";
      }
    }

    deviation /oc-opt-amp:optical-amplifier/oc-opt-amp:amplifiers/oc-opt-amp:amplifier/oc-opt-amp:config/oc-opt-amp:gain-range {
      deviate add {
        sonic-ext:field-name "gain-range";
      }
    }

    deviation /oc-opt-amp:optical-amplifier/oc-opt-amp:amplifiers/oc-opt-amp:amplifier/oc-opt-amp:config/oc-opt-amp:name {
      deviate add {
        sonic-ext:field-transformer "oa_name_field_xfmr";
      }
    }

    deviation /oc-opt-amp:optical-amplifier/oc-opt-amp:amplifiers/oc-opt-amp:amplifier/oc-opt-amp:config/oc-opt-amp:fiber-type-profile {
      deviate add {
        sonic-ext:field-name "fiber-type-profile";
      }
    }

    deviation /oc-opt-amp:optical-amplifier/oc-opt-amp:amplifiers/oc-opt-amp:amplifier/oc-opt-amp:config/oc-opt-amp:type {
      deviate add {
        sonic-ext:field-name "type";
      }
    }

    deviation /oc-opt-amp:optical-amplifier/oc-opt-amp:amplifiers/oc-opt-amp:amplifier/oc-opt-amp:config/oc-opt-amp:enabled {
      deviate add {
        sonic-ext:field-name "enabled";
      }
    }

    deviation /oc-opt-amp:optical-amplifier/oc-opt-amp:amplifiers/oc-opt-amp:amplifier/oc-opt-amp:state {
      deviate add {
        sonic-ext:db-name "STATE_DB";
        sonic-ext:table-name "AMPLIFIER_TABLE";
        sonic-ext:key-transformer "oa_name_key_xfmr";
      }
    }

    deviation /oc-opt-amp:optical-amplifier/oc-opt-amp:amplifiers/oc-opt-amp:amplifier/oc-opt-amp:state/oc-opt-amp:ingress-port {
      deviate add {
        sonic-ext:field-name "ingress-port";
      }
    }

    deviation /oc-opt-amp:optical-amplifier/oc-opt-amp:amplifiers/oc-opt-amp:amplifier/oc-opt-amp:state/oc-opt-amp:target-gain-tilt {
      deviate add {
        sonic-ext:field-name "target-gain-tilt";
      }
    }

    deviation /oc-opt-amp:optical-amplifier/oc-opt-amp:amplifiers/oc-opt-amp:amplifier/oc-opt-amp:state/oc-opt-amp:type {
      deviate add {
        sonic-ext:field-name "type";
      }
    }

    deviation /oc-opt-amp:optical-amplifier/oc-opt-amp:amplifiers/oc-opt-amp:amplifier/oc-opt-amp:state/oc-opt-amp:gain-range {
      deviate add {
        sonic-ext:field-name "gain-range";
      }
    }

    deviation /oc-opt-amp:optical-amplifier/oc-opt-amp:amplifiers/oc-opt-amp:amplifier/oc-opt-amp:state/oc-opt-amp:fiber-type-profile {
      deviate add {
        sonic-ext:field-name "fiber-type-profile";
      }
    }

    deviation /oc-opt-amp:optical-amplifier/oc-opt-amp:amplifiers/oc-opt-amp:amplifier/oc-opt-amp:state/oc-opt-amp:name {
      deviate add {
	sonic-ext:field-transformer "oa_name_field_xfmr";
      }
    }

    deviation /oc-opt-amp:optical-amplifier/oc-opt-amp:amplifiers/oc-opt-amp:amplifier/oc-opt-amp:state/oc-opt-amp:target-gain {
      deviate add {
        sonic-ext:field-name "target-gain";
      }
    }

    deviation /oc-opt-amp:optical-amplifier/oc-opt-amp:amplifiers/oc-opt-amp:amplifier/oc-opt-amp:state/oc-opt-amp:component {
      deviate add {
        sonic-ext:field-name "component";
      }
    }

    
    deviation /oc-opt-amp:optical-amplifier/oc-opt-amp:amplifiers/oc-opt-amp:amplifier/oc-opt-amp:state/oc-opt-amp:target-output-power {
      deviate add {
        sonic-ext:field-name "target-output-power";
      }
    }

     deviation /oc-opt-amp:optical-amplifier/oc-opt-amp:amplifiers/oc-opt-amp:amplifier/oc-opt-amp:state/oc-opt-amp:max-output-power {
      deviate add {
        sonic-ext:field-name "max-output-power";
      }
    }


   deviation /oc-opt-amp:optical-amplifier/oc-opt-amp:amplifiers/oc-opt-amp:amplifier/oc-opt-amp:state/oc-opt-amp:egress-port {
      deviate add {
        sonic-ext:field-name "egress-port";
      }
    }

    deviation /oc-opt-amp:optical-amplifier/oc-opt-amp:amplifiers/oc-opt-amp:amplifier/oc-opt-amp:state/oc-opt-amp:amp-mode {
      deviate add {
        sonic-ext:field-name "amp-mode";
      }
    }

    deviation /oc-opt-amp:optical-amplifier/oc-opt-amp:amplifiers/oc-opt-amp:amplifier/oc-opt-amp:state/oc-opt-amp:enabled {
      deviate add {
        sonic-ext:field-name "enabled";
      }
    }

    deviation /oc-opt-amp:optical-amplifier/oc-opt-amp:amplifiers/oc-opt-amp:amplifier/oc-opt-amp:name {
      deviate add {
      }
    }

    deviation /oc-opt-amp:optical-amplifier/oc-opt-amp:supervisory-channels {
      deviate add {
        sonic-ext:db-name "STATE_DB";
        sonic-ext:table-name "OSC_TABLE";
      }
    }

    deviation /oc-opt-amp:optical-amplifier/oc-opt-amp:supervisory-channels/oc-opt-amp:supervisory-channel {
      deviate add {
        sonic-ext:key-transformer "osc_key_xfmr";
      }
    }

    deviation /oc-opt-amp:optical-amplifier/oc-opt-amp:supervisory-channels/oc-opt-amp:supervisory-channel/oc-opt-amp:config {
      deviate add {
      }
    }

    deviation /oc-opt-amp:optical-amplifier/oc-opt-amp:supervisory-channels/oc-opt-amp:supervisory-channel/oc-opt-amp:config/oc-opt-amp:interface {
      deviate add {
        sonic-ext:field-transformer "osc_interface_field_xfmr";
      }
    }

    deviation /oc-opt-amp:optical-amplifier/oc-opt-amp:supervisory-channels/oc-opt-amp:supervisory-channel/oc-opt-amp:state {
      deviate add {
        sonic-ext:db-name "STATE_DB";
        sonic-ext:table-name "OSC_TABLE";
        sonic-ext:key-transformer "osc_key_xfmr";
      }
    }

    deviation /oc-opt-amp:optical-amplifier/oc-opt-amp:supervisory-channels/oc-opt-amp:supervisory-channel/oc-opt-amp:state/oc-opt-amp:output-frequency {
      deviate add {
        sonic-ext:field-name "output-frequency";
      }
    }

    deviation /oc-opt-amp:optical-amplifier/oc-opt-amp:supervisory-channels/oc-opt-amp:supervisory-channel/oc-opt-amp:state/oc-opt-amp:interface {
      deviate add {
        sonic-ext:field-transformer "osc_interface_field_xfmr";
      }
    }

    deviation /oc-opt-amp:optical-amplifier/oc-opt-amp:supervisory-channels/oc-opt-amp:supervisory-channel/oc-opt-amp:interface {
      deviate add {
      }
    }

    deviation /oc-opt-amp:optical-amplifier/oc-opt-amp:supervisory-channels/oc-opt-amp:supervisory-channel/oc-opt-amp:state/oc-opt-amp:output-power {
      deviate add {
        sonic-ext:db-name "COUNTERS_DB";
        sonic-ext:table-name "OSC";
        sonic-ext:key-transformer "osc_output_power_counter_key_xfmr";
      }
    }

    deviation /oc-opt-amp:optical-amplifier/oc-opt-amp:supervisory-channels/oc-opt-amp:supervisory-channel/oc-opt-amp:state/oc-opt-amp:output-power/oc-opt-amp:instant {
      deviate add {
        sonic-ext:field-name "instant";
      }
    }

    deviation /oc-opt-amp:optical-amplifier/oc-opt-amp:supervisory-channels/oc-opt-amp:supervisory-channel/oc-opt-amp:state/oc-opt-amp:output-power/oc-opt-amp:avg {
      deviate add {
        sonic-ext:field-name "avg";
      }
    }

    deviation /oc-opt-amp:optical-amplifier/oc-opt-amp:supervisory-channels/oc-opt-amp:supervisory-channel/oc-opt-amp:state/oc-opt-amp:output-power/oc-opt-amp:min {
      deviate add {
        sonic-ext:field-name "min";
      }
    }

    deviation /oc-opt-amp:optical-amplifier/oc-opt-amp:supervisory-channels/oc-opt-amp:supervisory-channel/oc-opt-amp:state/oc-opt-amp:output-power/oc-opt-amp:max {
      deviate add {
        sonic-ext:field-name "max";
      }
    }

    deviation /oc-opt-amp:optical-amplifier/oc-opt-amp:supervisory-channels/oc-opt-amp:supervisory-channel/oc-opt-amp:state/oc-opt-amp:output-power/oc-opt-amp:interval {
      deviate add {
        sonic-ext:field-name "interval";
      }
    }

    deviation /oc-opt-amp:optical-amplifier/oc-opt-amp:supervisory-channels/oc-opt-amp:supervisory-channel/oc-opt-amp:state/oc-opt-amp:output-power/oc-opt-amp:min-time {
      deviate add {
        sonic-ext:field-name "min-time";
      }
    }

    deviation /oc-opt-amp:optical-amplifier/oc-opt-amp:supervisory-channels/oc-opt-amp:supervisory-channel/oc-opt-amp:state/oc-opt-amp:output-power/oc-opt-amp:max-time {
      deviate add {
        sonic-ext:field-name "max-time";
      }
    }

    deviation /oc-opt-amp:optical-amplifier/oc-opt-amp:supervisory-channels/oc-opt-amp:supervisory-channel/oc-opt-amp:state/oc-opt-amp:laser-bias-current {
      deviate add {
        sonic-ext:db-name "COUNTERS_DB";
        sonic-ext:table-name "OSC";
        sonic-ext:key-transformer "osc_laser_bias_current_counter_key_xfmr";
      }
    }

    deviation /oc-opt-amp:optical-amplifier/oc-opt-amp:supervisory-channels/oc-opt-amp:supervisory-channel/oc-opt-amp:state/oc-opt-amp:laser-bias-current/oc-opt-amp:instant {
      deviate add {
        sonic-ext:field-name "instant";
      }
    }

    deviation /oc-opt-amp:optical-amplifier/oc-opt-amp:supervisory-channels/oc-opt-amp:supervisory-channel/oc-opt-amp:state/oc-opt-amp:laser-bias-current/oc-opt-amp:avg {
      deviate add {
		sonic-ext:field-name "avg";
      }
    }

    deviation /oc-opt-amp:optical-amplifier/oc-opt-amp:supervisory-channels/oc-opt-amp:supervisory-channel/oc-opt-amp:state/oc-opt-amp:laser-bias-current/oc-opt-amp:min {
      deviate add {
		sonic-ext:field-name "min";
      }
    }

    deviation /oc-opt-amp:optical-amplifier/oc-opt-amp:supervisory-channels/oc-opt-amp:supervisory-channel/oc-opt-amp:state/oc-opt-amp:laser-bias-current/oc-opt-amp:max {
      deviate add {
		sonic-ext:field-name "max";
      }
    }

    deviation /oc-opt-amp:optical-amplifier/oc-opt-amp:supervisory-channels/oc-opt-amp:supervisory-channel/oc-opt-amp:state/oc-opt-amp:laser-bias-current/oc-opt-amp:interval {
      deviate add {
		sonic-ext:field-name "interval";
      }
    }

    deviation /oc-opt-amp:optical-amplifier/oc-opt-amp:supervisory-channels/oc-opt-amp:supervisory-channel/oc-opt-amp:state/oc-opt-amp:laser-bias-current/oc-opt-amp:min-time {
      deviate add {
		sonic-ext:field-name "min-time";
      }
    }

    deviation /oc-opt-amp:optical-amplifier/oc-opt-amp:supervisory-channels/oc-opt-amp:supervisory-channel/oc-opt-amp:state/oc-opt-amp:laser-bias-current/oc-opt-amp:max-time {
      deviate add {
        sonic-ext:field-name "max-time";
      }
    }

    deviation /oc-opt-amp:optical-amplifier/oc-opt-amp:supervisory-channels/oc-opt-amp:supervisory-channel/oc-opt-amp:state/oc-opt-amp:input-power {
      deviate add {
        sonic-ext:db-name "COUNTERS_DB";
        sonic-ext:table-name "OSC";
        sonic-ext:key-transformer "osc_input_power_counter_key_xfmr";
      }
    }

    deviation /oc-opt-amp:optical-amplifier/oc-opt-amp:supervisory-channels/oc-opt-amp:supervisory-channel/oc-opt-amp:state/oc-opt-amp:input-power/oc-opt-amp:instant {
      deviate add {
        sonic-ext:field-name "instant";
      }
    }

    deviation /oc-opt-amp:optical-amplifier/oc-opt-amp:supervisory-channels/oc-opt-amp:supervisory-channel/oc-opt-amp:state/oc-opt-amp:input-power/oc-opt-amp:avg {
      deviate add {
		sonic-ext:field-name "avg";
      }
    }

    deviation /oc-opt-amp:optical-amplifier/oc-opt-amp:supervisory-channels/oc-opt-amp:supervisory-channel/oc-opt-amp:state/oc-opt-amp:input-power/oc-opt-amp:min {
      deviate add {
		sonic-ext:field-name "min";
      }
    }

    deviation /oc-opt-amp:optical-amplifier/oc-opt-amp:supervisory-channels/oc-opt-amp:supervisory-channel/oc-opt-amp:state/oc-opt-amp:input-power/oc-opt-amp:max {
      deviate add {
		sonic-ext:field-name "max";      }
    }

    deviation /oc-opt-amp:optical-amplifier/oc-opt-amp:supervisory-channels/oc-opt-amp:supervisory-channel/oc-opt-amp:state/oc-opt-amp:input-power/oc-opt-amp:interval {
      deviate add {
		sonic-ext:field-name "interval";
      }
    }

    deviation /oc-opt-amp:optical-amplifier/oc-opt-amp:supervisory-channels/oc-opt-amp:supervisory-channel/oc-opt-amp:state/oc-opt-amp:input-power/oc-opt-amp:min-time {
      deviate add {
		sonic-ext:field-name "min-time";
      }
    }

    deviation /oc-opt-amp:optical-amplifier/oc-opt-amp:supervisory-channels/oc-opt-amp:supervisory-channel/oc-opt-amp:state/oc-opt-amp:input-power/oc-opt-amp:max-time {
      deviate add {
		sonic-ext:field-name "max-time";
      }
    }

    deviation /oc-opt-amp:optical-amplifier/oc-opt-amp:amplifiers/oc-opt-amp:amplifier/oc-opt-amp:state/oc-opt-amp:output-power-l-band {
      deviate add {
        sonic-ext:db-name "COUNTERS_DB";
        sonic-ext:table-name "AMPLIFIER";
        sonic-ext:key-transformer "oa_counter_output_powerL_key_xfmr";
      }
    }

    deviation /oc-opt-amp:optical-amplifier/oc-opt-amp:amplifiers/oc-opt-amp:amplifier/oc-opt-amp:state/oc-opt-amp:output-power-l-band/oc-opt-amp:min {
      deviate add {
		sonic-ext:field-name "min";
      }
    }

    deviation /oc-opt-amp:optical-amplifier/oc-opt-amp:amplifiers/oc-opt-amp:amplifier/oc-opt-amp:state/oc-opt-amp:output-power-l-band/oc-opt-amp:max {
      deviate add {
		sonic-ext:field-name "max";
      }
    }

    deviation /oc-opt-amp:optical-amplifier/oc-opt-amp:amplifiers/oc-opt-amp:amplifier/oc-opt-amp:state/oc-opt-amp:output-power-l-band/oc-opt-amp:interval {
      deviate add {
		sonic-ext:field-name "interval";
      }
    }

    deviation /oc-opt-amp:optical-amplifier/oc-opt-amp:amplifiers/oc-opt-amp:amplifier/oc-opt-amp:state/oc-opt-amp:output-power-l-band/oc-opt-amp:min-time {
      deviate add {
		sonic-ext:field-name "min-time";
      }
    }

    deviation /oc-opt-amp:optical-amplifier/oc-opt-amp:amplifiers/oc-opt-amp:amplifier/oc-opt-amp:state/oc-opt-amp:output-power-l-band/oc-opt-amp:max-time {
      deviate add {
		sonic-ext:field-name "max-time";
      }
    }

    deviation /oc-opt-amp:optical-amplifier/oc-opt-amp:amplifiers/oc-opt-amp:amplifier/oc-opt-amp:state/oc-opt-amp:output-power-l-band/oc-opt-amp:instant {
      deviate add {
		sonic-ext:field-name "instant";
      }
    }

    deviation /oc-opt-amp:optical-amplifier/oc-opt-amp:amplifiers/oc-opt-amp:amplifier/oc-opt-amp:state/oc-opt-amp:output-power-l-band/oc-opt-amp:avg {
      deviate add {
		sonic-ext:field-name "avg";
      }
    }

    deviation /oc-opt-amp:optical-amplifier/oc-opt-amp:amplifiers/oc-opt-amp:amplifier/oc-opt-amp:state/oc-opt-amp:optical-return-loss {
      deviate add {
        sonic-ext:db-name "COUNTERS_DB";
        sonic-ext:table-name "AMPLIFIER";
        sonic-ext:key-transformer "oa_counter_optical_return_loss_key_xfmr";
      }
    }

    deviation /oc-opt-amp:optical-amplifier/oc-opt-amp:amplifiers/oc-opt-amp:amplifier/oc-opt-amp:state/oc-opt-amp:optical-return-loss/oc-opt-amp:interval {
      deviate add {
        sonic-ext:field-name "interval";
      }
    }

    deviation /oc-opt-amp:optical-amplifier/oc-opt-amp:amplifiers/oc-opt-amp:amplifier/oc-opt-amp:state/oc-opt-amp:optical-return-loss/oc-opt-amp:min-time {
      deviate add {
        sonic-ext:field-name "min-time";
      }
    }

    deviation /oc-opt-amp:optical-amplifier/oc-opt-amp:amplifiers/oc-opt-amp:amplifier/oc-opt-amp:state/oc-opt-amp:optical-return-loss/oc-opt-amp:max-time {
      deviate add {
        sonic-ext:field-name "max-time";
      }
    }

    deviation /oc-opt-amp:optical-amplifier/oc-opt-amp:amplifiers/oc-opt-amp:amplifier/oc-opt-amp:state/oc-opt-amp:optical-return-loss/oc-opt-amp:instant {
      deviate add {
        sonic-ext:field-name "instant";
      }
    }

    deviation /oc-opt-amp:optical-amplifier/oc-opt-amp:amplifiers/oc-opt-amp:amplifier/oc-opt-amp:state/oc-opt-amp:optical-return-loss/oc-opt-amp:avg {
      deviate add {
        sonic-ext:field-name "avg";
      }
    }

    deviation /oc-opt-amp:optical-amplifier/oc-opt-amp:amplifiers/oc-opt-amp:amplifier/oc-opt-amp:state/oc-opt-amp:optical-return-loss/oc-opt-amp:min {
      deviate add {
        sonic-ext:field-name "min";
      }
    }

    deviation /oc-opt-amp:optical-amplifier/oc-opt-amp:amplifiers/oc-opt-amp:amplifier/oc-opt-amp:state/oc-opt-amp:optical-return-loss/oc-opt-amp:max {
      deviate add {
        sonic-ext:field-name "max";
      }
    }
    
    deviation /oc-opt-amp:optical-amplifier/oc-opt-amp:amplifiers/oc-opt-amp:amplifier/oc-opt-amp:config/com-oplink-amplifier-ext:autolos {
      deviate add {
        sonic-ext:field-name "autolos";
      }
    }

    deviation /oc-opt-amp:optical-amplifier/oc-opt-amp:amplifiers/oc-opt-amp:amplifier/oc-opt-amp:config/com-oplink-amplifier-ext:apr-enabled {
      deviate add {
        sonic-ext:field-name "apr-enabled";
      }
    }
    
    deviation /oc-opt-amp:optical-amplifier/oc-opt-amp:amplifiers/oc-opt-amp:amplifier/oc-opt-amp:state/com-oplink-amplifier-ext:autolos {
      deviate add {
        sonic-ext:field-name "autolos";
      }
    }

    deviation /oc-opt-amp:optical-amplifier/oc-opt-amp:amplifiers/oc-opt-amp:amplifier/oc-opt-amp:state/com-oplink-amplifier-ext:apr-enabled {
      deviate add {
        sonic-ext:field-name "apr-enabled";
      }
    }

    deviation /oc-opt-amp:optical-amplifier/oc-opt-amp:amplifiers/oc-opt-amp:amplifier/oc-opt-amp:state/oc-opt-amp:min-gain {
      deviate add {
        sonic-ext:field-name "min-gain";
      }
    }

    deviation /oc-opt-amp:optical-amplifier/oc-opt-amp:amplifiers/oc-opt-amp:amplifier/oc-opt-amp:state/oc-opt-amp:output-power-c-band {
      deviate add {
        sonic-ext:db-name "COUNTERS_DB";
        sonic-ext:table-name "AMPLIFIER";
        sonic-ext:key-transformer "oa_counter_output_powerC_key_xfmr";
      }
    }

    deviation /oc-opt-amp:optical-amplifier/oc-opt-amp:amplifiers/oc-opt-amp:amplifier/oc-opt-amp:state/oc-opt-amp:output-power-c-band/oc-opt-amp:avg {
      deviate add {
		sonic-ext:field-name "avg";
      }
    }

    deviation /oc-opt-amp:optical-amplifier/oc-opt-amp:amplifiers/oc-opt-amp:amplifier/oc-opt-amp:state/oc-opt-amp:output-power-c-band/oc-opt-amp:min {
      deviate add {
        sonic-ext:field-name "min";
      }
    }

    deviation /oc-opt-amp:optical-amplifier/oc-opt-amp:amplifiers/oc-opt-amp:amplifier/oc-opt-amp:state/oc-opt-amp:output-power-c-band/oc-opt-amp:max {
      deviate add {
        sonic-ext:field-name "max";
      }
    }

    deviation /oc-opt-amp:optical-amplifier/oc-opt-amp:amplifiers/oc-opt-amp:amplifier/oc-opt-amp:state/oc-opt-amp:output-power-c-band/oc-opt-amp:interval {
      deviate add {
        sonic-ext:field-name "interval";
      }
    }

    deviation /oc-opt-amp:optical-amplifier/oc-opt-amp:amplifiers/oc-opt-amp:amplifier/oc-opt-amp:state/oc-opt-amp:output-power-c-band/oc-opt-amp:min-time {
      deviate add {
        sonic-ext:field-name "min-time";
      }
    }

    deviation /oc-opt-amp:optical-amplifier/oc-opt-amp:amplifiers/oc-opt-amp:amplifier/oc-opt-amp:state/oc-opt-amp:output-power-c-band/oc-opt-amp:max-time {
      deviate add {
        sonic-ext:field-name "max-time";
      }
    }

    deviation /oc-opt-amp:optical-amplifier/oc-opt-amp:amplifiers/oc-opt-amp:amplifier/oc-opt-amp:state/oc-opt-amp:output-power-c-band/oc-opt-amp:instant {
      deviate add {
        sonic-ext:field-name "instant";
      }
    }

    deviation /oc-opt-amp:optical-amplifier/oc-opt-amp:amplifiers/oc-opt-amp:amplifier/oc-opt-amp:state/oc-opt-amp:laser-bias-current {
      deviate add {
        sonic-ext:db-name "COUNTERS_DB";
        sonic-ext:table-name "AMPLIFIER";
        sonic-ext:key-transformer "oa_counter_laser_bias_key_xfmr";
      }
    }

    deviation /oc-opt-amp:optical-amplifier/oc-opt-amp:amplifiers/oc-opt-amp:amplifier/oc-opt-amp:state/oc-opt-amp:laser-bias-current/oc-opt-amp:max {
      deviate add {
        sonic-ext:field-name "max";
      }
    }

    deviation /oc-opt-amp:optical-amplifier/oc-opt-amp:amplifiers/oc-opt-amp:amplifier/oc-opt-amp:state/oc-opt-amp:laser-bias-current/oc-opt-amp:interval {
      deviate add {
        sonic-ext:field-name "interval";
      }
    }

    deviation /oc-opt-amp:optical-amplifier/oc-opt-amp:amplifiers/oc-opt-amp:amplifier/oc-opt-amp:state/oc-opt-amp:laser-bias-current/oc-opt-amp:min-time {
      deviate add {
        sonic-ext:field-name "min-time";
      }
    }

    deviation /oc-opt-amp:optical-amplifier/oc-opt-amp:amplifiers/oc-opt-amp:amplifier/oc-opt-amp:state/oc-opt-amp:laser-bias-current/oc-opt-amp:max-time {
      deviate add {
        sonic-ext:field-name "max-time";
      }
    }

    deviation /oc-opt-amp:optical-amplifier/oc-opt-amp:amplifiers/oc-opt-amp:amplifier/oc-opt-amp:state/oc-opt-amp:laser-bias-current/oc-opt-amp:instant {
      deviate add {
        sonic-ext:field-name "instant";
      }
    }

    deviation /oc-opt-amp:optical-amplifier/oc-opt-amp:amplifiers/oc-opt-amp:amplifier/oc-opt-amp:state/oc-opt-amp:laser-bias-current/oc-opt-amp:avg {
      deviate add {
        sonic-ext:field-name "avg";
      }
    }

    deviation /oc-opt-amp:optical-amplifier/oc-opt-amp:amplifiers/oc-opt-amp:amplifier/oc-opt-amp:state/oc-opt-amp:laser-bias-current/oc-opt-amp:min {
      deviate add {
        sonic-ext:field-name "min";
      }
    }

    deviation /oc-opt-amp:optical-amplifier/oc-opt-amp:amplifiers/oc-opt-amp:amplifier/oc-opt-amp:state/oc-opt-amp:input-power-c-band {
      deviate add {
        sonic-ext:db-name "COUNTERS_DB";
        sonic-ext:table-name "AMPLIFIER";
        sonic-ext:key-transformer "oa_counter_input_powerC_key_xfmr";
      }
    }

    deviation /oc-opt-amp:optical-amplifier/oc-opt-amp:amplifiers/oc-opt-amp:amplifier/oc-opt-amp:state/oc-opt-amp:input-power-c-band/oc-opt-amp:instant {
      deviate add {
        sonic-ext:field-name "instant";
      }
    }

    deviation /oc-opt-amp:optical-amplifier/oc-opt-amp:amplifiers/oc-opt-amp:amplifier/oc-opt-amp:state/oc-opt-amp:input-power-c-band/oc-opt-amp:avg {
      deviate add {
        sonic-ext:field-name "avg";
      }
    }

    deviation /oc-opt-amp:optical-amplifier/oc-opt-amp:amplifiers/oc-opt-amp:amplifier/oc-opt-amp:state/oc-opt-amp:input-power-c-band/oc-opt-amp:min {
      deviate add {
        sonic-ext:field-name "min";
      }
    }

    deviation /oc-opt-amp:optical-amplifier/oc-opt-amp:amplifiers/oc-opt-amp:amplifier/oc-opt-amp:state/oc-opt-amp:input-power-c-band/oc-opt-amp:max {
      deviate add {
        sonic-ext:field-name "max";
      }
    }

    deviation /oc-opt-amp:optical-amplifier/oc-opt-amp:amplifiers/oc-opt-amp:amplifier/oc-opt-amp:state/oc-opt-amp:input-power-c-band/oc-opt-amp:interval {
      deviate add {
        sonic-ext:field-name "interval";
      }
    }

    deviation /oc-opt-amp:optical-amplifier/oc-opt-amp:amplifiers/oc-opt-amp:amplifier/oc-opt-amp:state/oc-opt-amp:input-power-c-band/oc-opt-amp:min-time {
      deviate add {
        sonic-ext:field-name "min-time";
      }
    }

    deviation /oc-opt-amp:optical-amplifier/oc-opt-amp:amplifiers/oc-opt-amp:amplifier/oc-opt-amp:state/oc-opt-amp:input-power-c-band/oc-opt-amp:max-time {
      deviate add {
        sonic-ext:field-name "max-time";
      }
    }

    deviation /oc-opt-amp:optical-amplifier/oc-opt-amp:amplifiers/oc-opt-amp:amplifier/oc-opt-amp:state/oc-opt-amp:gain-range {
      deviate add {
        sonic-ext:field-name "gain-range";
      }
    }

    deviation /oc-opt-amp:optical-amplifier/oc-opt-amp:amplifiers/oc-opt-amp:amplifier/oc-opt-amp:state/oc-opt-amp:output-power-total {
      deviate add {
        sonic-ext:db-name "COUNTERS_DB";
        sonic-ext:table-name "AMPLIFIER";
        sonic-ext:key-transformer "oa_counter_output_power_total_key_xfmr";
      }
    }

    deviation /oc-opt-amp:optical-amplifier/oc-opt-amp:amplifiers/oc-opt-amp:amplifier/oc-opt-amp:state/oc-opt-amp:output-power-total/oc-opt-amp:max-time {
      deviate add {
        sonic-ext:field-name "max-time";
      }
    }

    deviation /oc-opt-amp:optical-amplifier/oc-opt-amp:amplifiers/oc-opt-amp:amplifier/oc-opt-amp:state/oc-opt-amp:output-power-total/oc-opt-amp:instant {
      deviate add {
        sonic-ext:field-name "instant";
      }
    }

    deviation /oc-opt-amp:optical-amplifier/oc-opt-amp:amplifiers/oc-opt-amp:amplifier/oc-opt-amp:state/oc-opt-amp:output-power-total/oc-opt-amp:avg {
      deviate add {
        sonic-ext:field-name "avg";
      }
    }

    deviation /oc-opt-amp:optical-amplifier/oc-opt-amp:amplifiers/oc-opt-amp:amplifier/oc-opt-amp:state/oc-opt-amp:output-power-total/oc-opt-amp:min {
      deviate add {
        sonic-ext:field-name "min";
      }
    }

    deviation /oc-opt-amp:optical-amplifier/oc-opt-amp:amplifiers/oc-opt-amp:amplifier/oc-opt-amp:state/oc-opt-amp:output-power-total/oc-opt-amp:max {
      deviate add {
        sonic-ext:field-name "max";
      }
    }

    deviation /oc-opt-amp:optical-amplifier/oc-opt-amp:amplifiers/oc-opt-amp:amplifier/oc-opt-amp:state/oc-opt-amp:output-power-total/oc-opt-amp:interval {
      deviate add {
        sonic-ext:field-name "interval";
      }
    }

    deviation /oc-opt-amp:optical-amplifier/oc-opt-amp:amplifiers/oc-opt-amp:amplifier/oc-opt-amp:state/oc-opt-amp:output-power-total/oc-opt-amp:min-time {
      deviate add {
        sonic-ext:field-name "min-time";
      }
    }
   
    deviation /oc-opt-amp:optical-amplifier/oc-opt-amp:amplifiers/oc-opt-amp:amplifier/oc-opt-amp:state/oc-opt-amp:input-power-total {
      deviate add {
        sonic-ext:db-name "COUNTERS_DB";
        sonic-ext:table-name "AMPLIFIER";
        sonic-ext:key-transformer "oa_counter_input_power_total_key_xfmr";
      }
    }

    deviation /oc-opt-amp:optical-amplifier/oc-opt-amp:amplifiers/oc-opt-amp:amplifier/oc-opt-amp:state/oc-opt-amp:input-power-total/oc-opt-amp:interval {
      deviate add {
        sonic-ext:field-name "interval";
      }
    }

    deviation /oc-opt-amp:optical-amplifier/oc-opt-amp:amplifiers/oc-opt-amp:amplifier/oc-opt-amp:state/oc-opt-amp:input-power-total/oc-opt-amp:min-time {
      deviate add {
        sonic-ext:field-name "min-time";
      }
    }

    deviation /oc-opt-amp:optical-amplifier/oc-opt-amp:amplifiers/oc-opt-amp:amplifier/oc-opt-amp:state/oc-opt-amp:input-power-total/oc-opt-amp:max-time {
      deviate add {
        sonic-ext:field-name "max-time";
      }
    }

    deviation /oc-opt-amp:optical-amplifier/oc-opt-amp:amplifiers/oc-opt-amp:amplifier/oc-opt-amp:state/oc-opt-amp:input-power-total/oc-opt-amp:instant {
      deviate add {
        sonic-ext:field-name "instant";
      }
    }

    deviation /oc-opt-amp:optical-amplifier/oc-opt-amp:amplifiers/oc-opt-amp:amplifier/oc-opt-amp:state/oc-opt-amp:input-power-total/oc-opt-amp:avg {
      deviate add {
        sonic-ext:field-name "avg";
      }
    }

    deviation /oc-opt-amp:optical-amplifier/oc-opt-amp:amplifiers/oc-opt-amp:amplifier/oc-opt-amp:state/oc-opt-amp:input-power-total/oc-opt-amp:min {
      deviate add {
        sonic-ext:field-name "min";
      }
    }

    deviation /oc-opt-amp:optical-amplifier/oc-opt-amp:amplifiers/oc-opt-amp:amplifier/oc-opt-amp:state/oc-opt-amp:input-power-total/oc-opt-amp:max {
      deviate add {
        sonic-ext:field-name "max";
      }
    }
  
    deviation /oc-opt-amp:optical-amplifier/oc-opt-amp:amplifiers/oc-opt-amp:amplifier/oc-opt-amp:state/oc-opt-amp:actual-gain {
      deviate add {
        sonic-ext:db-name "COUNTERS_DB";
        sonic-ext:table-name "AMPLIFIER";
        sonic-ext:key-transformer "oa_counter_actual_gain_key_xfmr";
      }
    }

    deviation /oc-opt-amp:optical-amplifier/oc-opt-amp:amplifiers/oc-opt-amp:amplifier/oc-opt-amp:state/oc-opt-amp:actual-gain/oc-opt-amp:max {
      deviate add {
        sonic-ext:field-name "max";
      }
    }

    deviation /oc-opt-amp:optical-amplifier/oc-opt-amp:amplifiers/oc-opt-amp:amplifier/oc-opt-amp:state/oc-opt-amp:actual-gain/oc-opt-amp:interval {
      deviate add {
        sonic-ext:field-name "interval";
      }
    }

    deviation /oc-opt-amp:optical-amplifier/oc-opt-amp:amplifiers/oc-opt-amp:amplifier/oc-opt-amp:state/oc-opt-amp:actual-gain/oc-opt-amp:min-time {
      deviate add {
        sonic-ext:field-name "min-time";
      }
    }

    deviation /oc-opt-amp:optical-amplifier/oc-opt-amp:amplifiers/oc-opt-amp:amplifier/oc-opt-amp:state/oc-opt-amp:actual-gain/oc-opt-amp:max-time {
      deviate add {
        sonic-ext:field-name "max-time";
      }
    }

    deviation /oc-opt-amp:optical-amplifier/oc-opt-amp:amplifiers/oc-opt-amp:amplifier/oc-opt-amp:state/oc-opt-amp:actual-gain/oc-opt-amp:instant {
      deviate add {
        sonic-ext:field-name "instant";
      }
    }

    deviation /oc-opt-amp:optical-amplifier/oc-opt-amp:amplifiers/oc-opt-amp:amplifier/oc-opt-amp:state/oc-opt-amp:actual-gain/oc-opt-amp:avg {
      deviate add {
        sonic-ext:field-name "avg";
      }
    }

    deviation /oc-opt-amp:optical-amplifier/oc-opt-amp:amplifiers/oc-opt-amp:amplifier/oc-opt-amp:state/oc-opt-amp:actual-gain/oc-opt-amp:min {
      deviate add {
        sonic-ext:field-name "min";
      }
    }

    deviation /oc-opt-amp:optical-amplifier/oc-opt-amp:amplifiers/oc-opt-amp:amplifier/oc-opt-amp:state/oc-opt-amp:input-power-l-band {
      deviate add {
        sonic-ext:db-name "COUNTERS_DB";
        sonic-ext:table-name "AMPLIFIER";
        sonic-ext:key-transformer "oa_counter_input_powerL_key_xfmr";
      }
    }

    deviation /oc-opt-amp:optical-amplifier/oc-opt-amp:amplifiers/oc-opt-amp:amplifier/oc-opt-amp:state/oc-opt-amp:input-power-l-band/oc-opt-amp:min {
      deviate add {
        sonic-ext:field-name "min";
      }
    }

    deviation /oc-opt-amp:optical-amplifier/oc-opt-amp:amplifiers/oc-opt-amp:amplifier/oc-opt-amp:state/oc-opt-amp:input-power-l-band/oc-opt-amp:max {
      deviate add {
        sonic-ext:field-name "max";
      }
    }

    deviation /oc-opt-amp:optical-amplifier/oc-opt-amp:amplifiers/oc-opt-amp:amplifier/oc-opt-amp:state/oc-opt-amp:input-power-l-band/oc-opt-amp:interval {
      deviate add {
        sonic-ext:field-name "interval";
      }
    }

    deviation /oc-opt-amp:optical-amplifier/oc-opt-amp:amplifiers/oc-opt-amp:amplifier/oc-opt-amp:state/oc-opt-amp:input-power-l-band/oc-opt-amp:min-time {
      deviate add {
        sonic-ext:field-name "min-time";
      }
    }

    deviation /oc-opt-amp:optical-amplifier/oc-opt-amp:amplifiers/oc-opt-amp:amplifier/oc-opt-amp:state/oc-opt-amp:input-power-l-band/oc-opt-amp:max-time {
      deviate add {
        sonic-ext:field-name "max-time";
      }
    }

    deviation /oc-opt-amp:optical-amplifier/oc-opt-amp:amplifiers/oc-opt-amp:amplifier/oc-opt-amp:state/oc-opt-amp:input-power-l-band/oc-opt-amp:instant {
      deviate add {
        sonic-ext:field-name "instant";
      }
    }

    deviation /oc-opt-amp:optical-amplifier/oc-opt-amp:amplifiers/oc-opt-amp:amplifier/oc-opt-amp:state/oc-opt-amp:input-power-l-band/oc-opt-amp:avg {
      deviate add {
        sonic-ext:field-name "avg";
      }
    }

    deviation /oc-opt-amp:optical-amplifier/oc-opt-amp:amplifiers/oc-opt-amp:amplifier/oc-opt-amp:state/oc-opt-amp:max-gain {
      deviate add {
        sonic-ext:field-name "max-gain";
      }
    }

    deviation /oc-opt-amp:optical-amplifier/oc-opt-amp:amplifiers/oc-opt-amp:amplifier/oc-opt-amp:state/oc-opt-amp:actual-gain-tilt {
      deviate add {
        sonic-ext:db-name "COUNTERS_DB";
        sonic-ext:table-name "AMPLIFIER";
        sonic-ext:key-transformer "oa_counter_actual_gain_tilt_key_xfmr";
      }
    }

    deviation /oc-opt-amp:optical-amplifier/oc-opt-amp:amplifiers/oc-opt-amp:amplifier/oc-opt-amp:state/oc-opt-amp:actual-gain-tilt/oc-opt-amp:max {
      deviate add {
        sonic-ext:field-name "max";
      }
    }

    deviation /oc-opt-amp:optical-amplifier/oc-opt-amp:amplifiers/oc-opt-amp:amplifier/oc-opt-amp:state/oc-opt-amp:actual-gain-tilt/oc-opt-amp:interval {
      deviate add {
        sonic-ext:field-name "interval";
      }
    }

    deviation /oc-opt-amp:optical-amplifier/oc-opt-amp:amplifiers/oc-opt-amp:amplifier/oc-opt-amp:state/oc-opt-amp:actual-gain-tilt/oc-opt-amp:min-time {
      deviate add {
        sonic-ext:field-name "min-time";
      }
    }

    deviation /oc-opt-amp:optical-amplifier/oc-opt-amp:amplifiers/oc-opt-amp:amplifier/oc-opt-amp:state/oc-opt-amp:actual-gain-tilt/oc-opt-amp:max-time {
      deviate add {
        sonic-ext:field-name "max-time";
      }
    }

    deviation /oc-opt-amp:optical-amplifier/oc-opt-amp:amplifiers/oc-opt-amp:amplifier/oc-opt-amp:state/oc-opt-amp:actual-gain-tilt/oc-opt-amp:instant {
      deviate add {
        sonic-ext:field-name "instant";
      }
    }
    
    deviation /oc-opt-amp:optical-amplifier/oc-opt-amp:amplifiers/oc-opt-amp:amplifier/oc-opt-amp:state/com-oplink-amplifier-ext:autolos {
      deviate add {
        sonic-ext:field-name "autolos";
      }
    }

    deviation /oc-opt-amp:optical-amplifier/oc-opt-amp:amplifiers/oc-opt-amp:amplifier/oc-opt-amp:state/com-oplink-amplifier-ext:apr-enabled {
      deviate add {
        sonic-ext:field-name "apr-enabled";
      }
    }
    
    deviation /oc-opt-amp:optical-amplifier/oc-opt-amp:supervisory-channels/oc-opt-amp:supervisory-channel/oc-opt-amp:state/com-oplink-amplifier-ext:enabled {
      deviate add {
        sonic-ext:field-name "enabled";
      }
    }

    deviation /oc-opt-amp:optical-amplifier/oc-opt-amp:supervisory-channels/oc-opt-amp:supervisory-channel/oc-opt-amp:state/com-oplink-amplifier-ext:drop-power {
      deviate add {
        sonic-ext:field-name "drop-power";
      }
    }

    deviation /oc-opt-amp:optical-amplifier/oc-opt-amp:supervisory-channels/oc-opt-amp:supervisory-channel/oc-opt-amp:state/com-oplink-amplifier-ext:add-power {
      deviate add {
        sonic-ext:field-name "add-power";
      }
    }

    deviation /oc-opt-amp:optical-amplifier/oc-opt-amp:amplifiers/oc-opt-amp:amplifier/oc-opt-amp:state/oc-opt-amp:actual-gain-tilt/oc-opt-amp:avg {
      deviate add {
        sonic-ext:field-name "avg";
      }
    }

    deviation /oc-opt-amp:optical-amplifier/oc-opt-amp:amplifiers/oc-opt-amp:amplifier/oc-opt-amp:state/oc-opt-amp:actual-gain-tilt/oc-opt-amp:min {
      deviate add {
        sonic-ext:field-name "min";
      }
    }
}
