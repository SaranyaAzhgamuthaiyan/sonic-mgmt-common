module openconfig-transport-line-protection-annot {

	yang-version "";

	namespace "http://openconfig.net/yang/annotation/oc-line-protect-annot";
	prefix "oc-line-protect-annot";

	import openconfig-extensions { prefix oc-ext; }
	import openconfig-types { prefix oc-types; }
	import openconfig-platform { prefix oc-platform; }
	import openconfig-transport-line-protection { prefix oc-line-protect; }
	import sonic-extensions { prefix sonic-ext; }

	deviation /oc-line-protect:aps {
		deviate add {
                        sonic-ext:subscribe-on-change "enable";
                        sonic-ext:get-namespace "aps_name_get_namespace_xfmr";
		}
	}

	deviation /oc-line-protect:aps/oc-line-protect:aps-modules {
		deviate add {
			sonic-ext:table-name "APS";
        	}
	}

	deviation /oc-line-protect:aps/oc-line-protect:aps-modules/oc-line-protect:aps-module {
		deviate add {
			sonic-ext:key-transformer "aps_name_key_xfmr";
		}
	}
        
	deviation /oc-line-protect:aps/oc-line-protect:aps-modules/oc-line-protect:aps-module/oc-line-protect:config {
		deviate add {
		}
	}

	deviation /oc-line-protect:aps/oc-line-protect:aps-modules/oc-line-protect:aps-module/oc-line-protect:config/oc-line-protect:force-to-port {
		deviate add {
			sonic-ext:field-name "force-to-port"; 
		}
	}

	deviation /oc-line-protect:aps/oc-line-protect:aps-modules/oc-line-protect:aps-module/oc-line-protect:config/oc-line-protect:name {
		deviate add {
			sonic-ext:field-transformer "aps_name_field_xfmr"; 
		}
	}
        
	deviation /oc-line-protect:aps/oc-line-protect:aps-modules/oc-line-protect:aps-module/oc-line-protect:state {
		deviate add {
			sonic-ext:db-name "STATE_DB";
			sonic-ext:table-name "APS_TABLE";
			sonic-ext:key-transformer "aps_name_key_xfmr"; 
		}
	}

	deviation /oc-line-protect:aps/oc-line-protect:aps-modules/oc-line-protect:aps-module/oc-line-protect:state/oc-line-protect:primary-switch-hysteresis {
		deviate add {
			sonic-ext:field-name "primary-switch-hysteresis";
		}
	}

	deviation /oc-line-protect:aps/oc-line-protect:aps-modules/oc-line-protect:aps-module/oc-line-protect:state/oc-line-protect:primary-switch-threshold {
		deviate add {
			sonic-ext:field-name "primary-switch-threshold";
		}
	}

	deviation /oc-line-protect:aps/oc-line-protect:aps-modules/oc-line-protect:aps-module/oc-line-protect:state/oc-line-protect:relative-switch-threshold-offset {
		deviate add {
			sonic-ext:field-name "relative-switch-threshold-offset";
		}
	}

	deviation /oc-line-protect:aps/oc-line-protect:aps-modules/oc-line-protect:aps-module/oc-line-protect:state/oc-line-protect:force-to-port {
		deviate add {
			sonic-ext:field-name "force-to-port"; //type enumersation need to check how it is working..
		}
	}

	deviation /oc-line-protect:aps/oc-line-protect:aps-modules/oc-line-protect:aps-module/oc-line-protect:state/oc-line-protect:hold-off-time {
		deviate add {
			sonic-ext:field-name "hold-off-time";
		}
	}

	deviation /oc-line-protect:aps/oc-line-protect:aps-modules/oc-line-protect:aps-module/oc-line-protect:state/oc-line-protect:active-path {
		deviate add {
			sonic-ext:field-name "active-path";
		}
	}

	deviation /oc-line-protect:aps/oc-line-protect:aps-modules/oc-line-protect:aps-module/oc-line-protect:state/oc-line-protect:revertive {
		deviate add {
			sonic-ext:field-name "revertive";
		}
	}

	deviation /oc-line-protect:aps/oc-line-protect:aps-modules/oc-line-protect:aps-module/oc-line-protect:state/oc-line-protect:secondary-switch-threshold {
		deviate add {
			sonic-ext:field-name "secondary-switch-threshold";
		}
	}

	deviation /oc-line-protect:aps/oc-line-protect:aps-modules/oc-line-protect:aps-module/oc-line-protect:state/oc-line-protect:relative-switch-threshold {
		deviate add {
			sonic-ext:field-name "relative-switch-threshold";
		}
	}

	deviation /oc-line-protect:aps/oc-line-protect:aps-modules/oc-line-protect:aps-module/oc-line-protect:state/oc-line-protect:name {
		deviate add {
			sonic-ext:field-transformer "aps_name_field_xfmr"; 
		}
	}

	deviation /oc-line-protect:aps/oc-line-protect:aps-modules/oc-line-protect:aps-module/oc-line-protect:state/oc-line-protect:wait-to-restore-time {
		deviate add {
			sonic-ext:field-name "wait-to-restore-time";
		}
	}
     
	deviation /oc-line-protect:aps/oc-line-protect:aps-modules/oc-line-protect:aps-module/oc-line-protect:ports {
		deviate add {
			sonic-ext:table-name "APS_PORT";
		}
	}

	deviation /oc-line-protect:aps/oc-line-protect:aps-modules/oc-line-protect:aps-module/oc-line-protect:ports/oc-line-protect:common-output {
		deviate add {
			sonic-ext:key-transformer "aps_port_commonOut_key_xfmr";
		}
	}

	deviation /oc-line-protect:aps/oc-line-protect:aps-modules/oc-line-protect:aps-module/oc-line-protect:ports/oc-line-protect:common-output/oc-line-protect:state {
		deviate add {
			sonic-ext:db-name "STATE_DB";
			sonic-ext:table-name "APS_PORT_TABLE";
			sonic-ext:key-transformer "aps_port_commonOut_key_xfmr";
		}
	}

	deviation /oc-line-protect:aps/oc-line-protect:aps-modules/oc-line-protect:aps-module/oc-line-protect:ports/oc-line-protect:common-output/oc-line-protect:state/oc-line-protect:target-attenuation {
		deviate add {
			sonic-ext:field-name "target-attenuation";       
		}
	}

	deviation /oc-line-protect:aps/oc-line-protect:aps-modules/oc-line-protect:aps-module/oc-line-protect:ports/oc-line-protect:common-output/oc-line-protect:state/oc-line-protect:optical-power {
		deviate add {
			sonic-ext:db-name "COUNTERS_DB";
			sonic-ext:table-name "APS_PORT";
			sonic-ext:key-transformer "aps_counter_commonOut_key_xfmr";
		}
	}

	deviation /oc-line-protect:aps/oc-line-protect:aps-modules/oc-line-protect:aps-module/oc-line-protect:ports/oc-line-protect:common-output/oc-line-protect:state/oc-line-protect:optical-power/oc-line-protect:instant {
		deviate add {
			sonic-ext:field-name "instant"; 
		}
	}

	deviation /oc-line-protect:aps/oc-line-protect:aps-modules/oc-line-protect:aps-module/oc-line-protect:ports/oc-line-protect:common-output/oc-line-protect:state/oc-line-protect:optical-power/oc-line-protect:avg {
		deviate add {
			sonic-ext:field-name "avg";
		}
	}

	deviation /oc-line-protect:aps/oc-line-protect:aps-modules/oc-line-protect:aps-module/oc-line-protect:ports/oc-line-protect:common-output/oc-line-protect:state/oc-line-protect:optical-power/oc-line-protect:min {
		deviate add {
			sonic-ext:field-name "min";
		}
	}

	deviation /oc-line-protect:aps/oc-line-protect:aps-modules/oc-line-protect:aps-module/oc-line-protect:ports/oc-line-protect:common-output/oc-line-protect:state/oc-line-protect:optical-power/oc-line-protect:max {
		deviate add {
			sonic-ext:field-name "max";
		}
	}

	deviation /oc-line-protect:aps/oc-line-protect:aps-modules/oc-line-protect:aps-module/oc-line-protect:ports/oc-line-protect:common-output/oc-line-protect:state/oc-line-protect:optical-power/oc-line-protect:interval {
		deviate add {
			sonic-ext:field-name "interval";
		}
	}

	deviation /oc-line-protect:aps/oc-line-protect:aps-modules/oc-line-protect:aps-module/oc-line-protect:ports/oc-line-protect:common-output/oc-line-protect:state/oc-line-protect:optical-power/oc-line-protect:max-time {
		deviate add {
			sonic-ext:field-name "max-time";
		}
	}

	deviation /oc-line-protect:aps/oc-line-protect:aps-modules/oc-line-protect:aps-module/oc-line-protect:ports/oc-line-protect:common-output/oc-line-protect:state/oc-line-protect:optical-power/oc-line-protect:min-time {
		deviate add {
			sonic-ext:field-name "min-time";
		}
	}

	deviation /oc-line-protect:aps/oc-line-protect:aps-modules/oc-line-protect:aps-module/oc-line-protect:ports/oc-line-protect:common-output/oc-line-protect:state/oc-line-protect:attenuation {
		deviate add {
			sonic-ext:field-name "attenuation";
		}
	}

	deviation /oc-line-protect:aps/oc-line-protect:aps-modules/oc-line-protect:aps-module/oc-line-protect:ports/oc-line-protect:common-output/oc-line-protect:config {
		deviate add {
		}
	}

	deviation /oc-line-protect:aps/oc-line-protect:aps-modules/oc-line-protect:aps-module/oc-line-protect:ports/oc-line-protect:line-primary-in {
		deviate add {
			sonic-ext:key-transformer "aps_port_LinePrimaryIn_key_xfmr";
		}
	}

	deviation /oc-line-protect:aps/oc-line-protect:aps-modules/oc-line-protect:aps-module/oc-line-protect:ports/oc-line-protect:line-primary-in/oc-line-protect:state {
		deviate add {
			sonic-ext:db-name "STATE_DB";
			sonic-ext:table-name "APS_PORT_TABLE";
			sonic-ext:key-transformer "aps_port_LinePrimaryIn_key_xfmr";
		}
	}

	deviation /oc-line-protect:aps/oc-line-protect:aps-modules/oc-line-protect:aps-module/oc-line-protect:ports/oc-line-protect:line-primary-in/oc-line-protect:state/oc-line-protect:enabled {
		deviate add {
			sonic-ext:field-name "enabled";
		}
	}

	deviation /oc-line-protect:aps/oc-line-protect:aps-modules/oc-line-protect:aps-module/oc-line-protect:ports/oc-line-protect:line-primary-in/oc-line-protect:state/oc-line-protect:attenuation {
		deviate add {
			sonic-ext:field-name "attenuation";
		}
	}

	deviation /oc-line-protect:aps/oc-line-protect:aps-modules/oc-line-protect:aps-module/oc-line-protect:ports/oc-line-protect:line-primary-in/oc-line-protect:state/oc-line-protect:optical-power {
		deviate add {
			sonic-ext:db-name "COUNTERS_DB";
			sonic-ext:table-name "APS_PORT";
			sonic-ext:key-transformer "aps_counter_linePrimaryIn_key_xfmr";
		}
	}

	deviation /oc-line-protect:aps/oc-line-protect:aps-modules/oc-line-protect:aps-module/oc-line-protect:ports/oc-line-protect:line-primary-in/oc-line-protect:state/oc-line-protect:optical-power/oc-line-protect:instant {
		deviate add {
			sonic-ext:field-name "instant";
		}
	}

	deviation /oc-line-protect:aps/oc-line-protect:aps-modules/oc-line-protect:aps-module/oc-line-protect:ports/oc-line-protect:line-primary-in/oc-line-protect:state/oc-line-protect:optical-power/oc-line-protect:avg {
		deviate add {
			sonic-ext:field-name "avg";
		}
	}

	deviation /oc-line-protect:aps/oc-line-protect:aps-modules/oc-line-protect:aps-module/oc-line-protect:ports/oc-line-protect:line-primary-in/oc-line-protect:state/oc-line-protect:optical-power/oc-line-protect:min {
		deviate add {
			sonic-ext:field-name "min"; 
		}
	}

	deviation /oc-line-protect:aps/oc-line-protect:aps-modules/oc-line-protect:aps-module/oc-line-protect:ports/oc-line-protect:line-primary-in/oc-line-protect:state/oc-line-protect:optical-power/oc-line-protect:max {
		deviate add {
			sonic-ext:field-name "max";
		}
	}

	deviation /oc-line-protect:aps/oc-line-protect:aps-modules/oc-line-protect:aps-module/oc-line-protect:ports/oc-line-protect:line-primary-in/oc-line-protect:state/oc-line-protect:optical-power/oc-line-protect:interval {
		deviate add {
			sonic-ext:field-name "interval";
		}
	}

	deviation /oc-line-protect:aps/oc-line-protect:aps-modules/oc-line-protect:aps-module/oc-line-protect:ports/oc-line-protect:line-primary-in/oc-line-protect:state/oc-line-protect:optical-power/oc-line-protect:max-time {
		deviate add {
			sonic-ext:field-name "max-time";
		}
	}

	deviation /oc-line-protect:aps/oc-line-protect:aps-modules/oc-line-protect:aps-module/oc-line-protect:ports/oc-line-protect:line-primary-in/oc-line-protect:state/oc-line-protect:optical-power/oc-line-protect:min-time {
		deviate add {
			sonic-ext:field-name "min-time";
		}
	}

	deviation /oc-line-protect:aps/oc-line-protect:aps-modules/oc-line-protect:aps-module/oc-line-protect:ports/oc-line-protect:line-primary-in/oc-line-protect:state/oc-line-protect:target-attenuation {
		deviate add {
			sonic-ext:field-name "target-attenuation";
		}
	}

	deviation /oc-line-protect:aps/oc-line-protect:aps-modules/oc-line-protect:aps-module/oc-line-protect:ports/oc-line-protect:line-primary-in/oc-line-protect:config {
		deviate add {
		}
	}

	deviation /oc-line-protect:aps/oc-line-protect:aps-modules/oc-line-protect:aps-module/oc-line-protect:ports/oc-line-protect:line-primary-out {
		deviate add {
			sonic-ext:key-transformer "aps_port_LinePrimaryOut_key_xfmr";
		}
	}

	deviation /oc-line-protect:aps/oc-line-protect:aps-modules/oc-line-protect:aps-module/oc-line-protect:ports/oc-line-protect:line-primary-out/oc-line-protect:state {
		deviate add {
			sonic-ext:db-name "STATE_DB";
			sonic-ext:table-name "APS_PORT_TABLE";
			sonic-ext:key-transformer "aps_port_LinePrimaryOut_key_xfmr";
		}
	}

	deviation /oc-line-protect:aps/oc-line-protect:aps-modules/oc-line-protect:aps-module/oc-line-protect:ports/oc-line-protect:line-primary-out/oc-line-protect:state/oc-line-protect:optical-power {
		deviate add {
			sonic-ext:db-name "COUNTERS_DB";
			sonic-ext:table-name "APS_PORT";
			sonic-ext:key-transformer "aps_counter_linePrimaryOut_key_xfmr";
		}
	}

	deviation /oc-line-protect:aps/oc-line-protect:aps-modules/oc-line-protect:aps-module/oc-line-protect:ports/oc-line-protect:line-primary-out/oc-line-protect:state/oc-line-protect:optical-power/oc-line-protect:max-time {
		deviate add {
			sonic-ext:field-name "max-time";
		}
	}

	deviation /oc-line-protect:aps/oc-line-protect:aps-modules/oc-line-protect:aps-module/oc-line-protect:ports/oc-line-protect:line-primary-out/oc-line-protect:state/oc-line-protect:optical-power/oc-line-protect:min-time {
		deviate add {
			sonic-ext:field-name "min-time";
		}
	}

	deviation /oc-line-protect:aps/oc-line-protect:aps-modules/oc-line-protect:aps-module/oc-line-protect:ports/oc-line-protect:line-primary-out/oc-line-protect:state/oc-line-protect:optical-power/oc-line-protect:instant {
		deviate add {
			sonic-ext:field-name "instant";
		}
	}

	deviation /oc-line-protect:aps/oc-line-protect:aps-modules/oc-line-protect:aps-module/oc-line-protect:ports/oc-line-protect:line-primary-out/oc-line-protect:state/oc-line-protect:optical-power/oc-line-protect:avg {
		deviate add {
			sonic-ext:field-name "avg";
		}
	}

	deviation /oc-line-protect:aps/oc-line-protect:aps-modules/oc-line-protect:aps-module/oc-line-protect:ports/oc-line-protect:line-primary-out/oc-line-protect:state/oc-line-protect:optical-power/oc-line-protect:min {
		deviate add {
			sonic-ext:field-name "min";
		}
	}

	deviation /oc-line-protect:aps/oc-line-protect:aps-modules/oc-line-protect:aps-module/oc-line-protect:ports/oc-line-protect:line-primary-out/oc-line-protect:state/oc-line-protect:optical-power/oc-line-protect:max {
		deviate add {
			sonic-ext:field-name "max";
		}
	}

	deviation /oc-line-protect:aps/oc-line-protect:aps-modules/oc-line-protect:aps-module/oc-line-protect:ports/oc-line-protect:line-primary-out/oc-line-protect:state/oc-line-protect:optical-power/oc-line-protect:interval {
		deviate add {
			sonic-ext:field-name "interval";
		}
	}

	deviation /oc-line-protect:aps/oc-line-protect:aps-modules/oc-line-protect:aps-module/oc-line-protect:ports/oc-line-protect:line-primary-out/oc-line-protect:state/oc-line-protect:target-attenuation {
		deviate add {
			sonic-ext:field-name "target-attenuation";
		}
	}

	deviation /oc-line-protect:aps/oc-line-protect:aps-modules/oc-line-protect:aps-module/oc-line-protect:ports/oc-line-protect:line-primary-out/oc-line-protect:state/oc-line-protect:attenuation {
		deviate add {
			sonic-ext:field-name "attenuation";
		}
	}

	deviation /oc-line-protect:aps/oc-line-protect:aps-modules/oc-line-protect:aps-module/oc-line-protect:ports/oc-line-protect:line-primary-out/oc-line-protect:config {
		deviate add {
		}
	}

	deviation /oc-line-protect:aps/oc-line-protect:aps-modules/oc-line-protect:aps-module/oc-line-protect:ports/oc-line-protect:line-secondary-in {
		deviate add {
			sonic-ext:key-transformer "aps_port_lineSecondaryIn_key_xfmr";  
		}
	}

	deviation /oc-line-protect:aps/oc-line-protect:aps-modules/oc-line-protect:aps-module/oc-line-protect:ports/oc-line-protect:line-secondary-in/oc-line-protect:state {
		deviate add {
			sonic-ext:db-name "STATE_DB";
			sonic-ext:table-name "APS_PORT_TABLE";
			sonic-ext:key-transformer "aps_port_lineSecondaryIn_key_xfmr";
		}
	}

	deviation /oc-line-protect:aps/oc-line-protect:aps-modules/oc-line-protect:aps-module/oc-line-protect:ports/oc-line-protect:line-secondary-in/oc-line-protect:state/oc-line-protect:attenuation {
		deviate add {
			sonic-ext:field-name "attenuation";
		}
	}

	deviation /oc-line-protect:aps/oc-line-protect:aps-modules/oc-line-protect:aps-module/oc-line-protect:ports/oc-line-protect:line-secondary-in/oc-line-protect:state/oc-line-protect:optical-power {
		deviate add {
			sonic-ext:db-name "COUNTERS_DB";
			sonic-ext:table-name "APS_PORT";
			sonic-ext:key-transformer "aps_counter_lineSecondaryIn_key_xfmr";
		}
	}

	deviation /oc-line-protect:aps/oc-line-protect:aps-modules/oc-line-protect:aps-module/oc-line-protect:ports/oc-line-protect:line-secondary-in/oc-line-protect:state/oc-line-protect:optical-power/oc-line-protect:avg {
		deviate add {
			sonic-ext:field-name "avg";
		}
	}

	deviation /oc-line-protect:aps/oc-line-protect:aps-modules/oc-line-protect:aps-module/oc-line-protect:ports/oc-line-protect:line-secondary-in/oc-line-protect:state/oc-line-protect:optical-power/oc-line-protect:min {
		deviate add {
			sonic-ext:field-name "min";
		}
	}

	deviation /oc-line-protect:aps/oc-line-protect:aps-modules/oc-line-protect:aps-module/oc-line-protect:ports/oc-line-protect:line-secondary-in/oc-line-protect:state/oc-line-protect:optical-power/oc-line-protect:max {
		deviate add {
			sonic-ext:field-name "max";
		}
	}

	deviation /oc-line-protect:aps/oc-line-protect:aps-modules/oc-line-protect:aps-module/oc-line-protect:ports/oc-line-protect:line-secondary-in/oc-line-protect:state/oc-line-protect:optical-power/oc-line-protect:interval {
		deviate add {
			sonic-ext:field-name "interval";
		}
	}

	deviation /oc-line-protect:aps/oc-line-protect:aps-modules/oc-line-protect:aps-module/oc-line-protect:ports/oc-line-protect:line-secondary-in/oc-line-protect:state/oc-line-protect:optical-power/oc-line-protect:max-time {
		deviate add {
			sonic-ext:field-name "max-time";
		}
	}

	deviation /oc-line-protect:aps/oc-line-protect:aps-modules/oc-line-protect:aps-module/oc-line-protect:ports/oc-line-protect:line-secondary-in/oc-line-protect:state/oc-line-protect:optical-power/oc-line-protect:min-time {
		deviate add {
			sonic-ext:field-name "min-time";
		}
	}

	deviation /oc-line-protect:aps/oc-line-protect:aps-modules/oc-line-protect:aps-module/oc-line-protect:ports/oc-line-protect:line-secondary-in/oc-line-protect:state/oc-line-protect:optical-power/oc-line-protect:instant {
		deviate add {
			sonic-ext:field-name "instant";
		}
	}

	deviation /oc-line-protect:aps/oc-line-protect:aps-modules/oc-line-protect:aps-module/oc-line-protect:ports/oc-line-protect:line-secondary-in/oc-line-protect:state/oc-line-protect:enabled {
		deviate add {
			sonic-ext:field-name "enabled";
		}
	}

	deviation /oc-line-protect:aps/oc-line-protect:aps-modules/oc-line-protect:aps-module/oc-line-protect:ports/oc-line-protect:line-secondary-in/oc-line-protect:state/oc-line-protect:target-attenuation {
		deviate add {
			sonic-ext:field-name "target-attenuation";
		}
	}

	deviation /oc-line-protect:aps/oc-line-protect:aps-modules/oc-line-protect:aps-module/oc-line-protect:ports/oc-line-protect:line-secondary-in/oc-line-protect:config {
		deviate add {
		}
	}

	deviation /oc-line-protect:aps/oc-line-protect:aps-modules/oc-line-protect:aps-module/oc-line-protect:ports/oc-line-protect:line-secondary-out {
		deviate add {
			sonic-ext:key-transformer "aps_port_lineSecondaryOut_key_xfmr";
		}
	}

	deviation /oc-line-protect:aps/oc-line-protect:aps-modules/oc-line-protect:aps-module/oc-line-protect:ports/oc-line-protect:line-secondary-out/oc-line-protect:config {
		deviate add {
		}
	}

	deviation /oc-line-protect:aps/oc-line-protect:aps-modules/oc-line-protect:aps-module/oc-line-protect:ports/oc-line-protect:line-secondary-out/oc-line-protect:state {
		deviate add {
			sonic-ext:db-name "STATE_DB";
			sonic-ext:table-name "APS_PORT_TABLE";
			sonic-ext:key-transformer "aps_port_lineSecondaryOut_key_xfmr";
		}
	}

	deviation /oc-line-protect:aps/oc-line-protect:aps-modules/oc-line-protect:aps-module/oc-line-protect:ports/oc-line-protect:line-secondary-out/oc-line-protect:state/oc-line-protect:target-attenuation {
		deviate add {
			sonic-ext:field-name "target-attenuation"; 
		}
	}

	deviation /oc-line-protect:aps/oc-line-protect:aps-modules/oc-line-protect:aps-module/oc-line-protect:ports/oc-line-protect:line-secondary-out/oc-line-protect:state/oc-line-protect:attenuation {
		deviate add {
			sonic-ext:field-name "attenuation";
		}
	}

	deviation /oc-line-protect:aps/oc-line-protect:aps-modules/oc-line-protect:aps-module/oc-line-protect:ports/oc-line-protect:line-secondary-out/oc-line-protect:state/oc-line-protect:optical-power {
		deviate add {
			sonic-ext:db-name "COUNTERS_DB";
			sonic-ext:table-name "APS_PORT";
			sonic-ext:key-transformer "aps_counter_lineSecondaryOut_key_xfmr";
		}
	}

	deviation /oc-line-protect:aps/oc-line-protect:aps-modules/oc-line-protect:aps-module/oc-line-protect:ports/oc-line-protect:line-secondary-out/oc-line-protect:state/oc-line-protect:optical-power/oc-line-protect:min-time {
		deviate add {
			sonic-ext:field-name "min-time";
		}
	}

	deviation /oc-line-protect:aps/oc-line-protect:aps-modules/oc-line-protect:aps-module/oc-line-protect:ports/oc-line-protect:line-secondary-out/oc-line-protect:state/oc-line-protect:optical-power/oc-line-protect:instant {
		deviate add {
			sonic-ext:field-name "instant";
		}
	}

	deviation /oc-line-protect:aps/oc-line-protect:aps-modules/oc-line-protect:aps-module/oc-line-protect:ports/oc-line-protect:line-secondary-out/oc-line-protect:state/oc-line-protect:optical-power/oc-line-protect:avg {
		deviate add {
			sonic-ext:field-name "avg";
		}
	}

	deviation /oc-line-protect:aps/oc-line-protect:aps-modules/oc-line-protect:aps-module/oc-line-protect:ports/oc-line-protect:line-secondary-out/oc-line-protect:state/oc-line-protect:optical-power/oc-line-protect:min {
		deviate add {
			sonic-ext:field-name "min";
		}
	}

	deviation /oc-line-protect:aps/oc-line-protect:aps-modules/oc-line-protect:aps-module/oc-line-protect:ports/oc-line-protect:line-secondary-out/oc-line-protect:state/oc-line-protect:optical-power/oc-line-protect:max {
		deviate add {
			sonic-ext:field-name "max";
		}
	}

	deviation /oc-line-protect:aps/oc-line-protect:aps-modules/oc-line-protect:aps-module/oc-line-protect:ports/oc-line-protect:line-secondary-out/oc-line-protect:state/oc-line-protect:optical-power/oc-line-protect:interval {
		deviate add {
			sonic-ext:field-name "interval";
		}
	}

	deviation /oc-line-protect:aps/oc-line-protect:aps-modules/oc-line-protect:aps-module/oc-line-protect:ports/oc-line-protect:line-secondary-out/oc-line-protect:state/oc-line-protect:optical-power/oc-line-protect:max-time {
		deviate add {
			sonic-ext:field-name "max-time";
		}
	}

	deviation /oc-line-protect:aps/oc-line-protect:aps-modules/oc-line-protect:aps-module/oc-line-protect:ports/oc-line-protect:common-in {
		deviate add {
			sonic-ext:key-transformer "aps_port_commonIn_key_xfmr";
		}
	}

	deviation /oc-line-protect:aps/oc-line-protect:aps-modules/oc-line-protect:aps-module/oc-line-protect:ports/oc-line-protect:common-in/oc-line-protect:config {
		deviate add {
		}
	}

	deviation /oc-line-protect:aps/oc-line-protect:aps-modules/oc-line-protect:aps-module/oc-line-protect:ports/oc-line-protect:common-in/oc-line-protect:state {
		deviate add {
			sonic-ext:db-name "STATE_DB";
			sonic-ext:table-name "APS_PORT_TABLE";
			sonic-ext:key-transformer "aps_port_commonIn_key_xfmr";
		}
	}

	deviation /oc-line-protect:aps/oc-line-protect:aps-modules/oc-line-protect:aps-module/oc-line-protect:ports/oc-line-protect:common-in/oc-line-protect:state/oc-line-protect:optical-power {
		deviate add {
			sonic-ext:db-name "COUNTERS_DB";
			sonic-ext:table-name "APS_PORT";
			sonic-ext:key-transformer "aps_counter_commonIn_key_xfmr";
		}
	}

	deviation /oc-line-protect:aps/oc-line-protect:aps-modules/oc-line-protect:aps-module/oc-line-protect:ports/oc-line-protect:common-in/oc-line-protect:state/oc-line-protect:optical-power/oc-line-protect:min {
		deviate add {
			sonic-ext:field-name "min";
		}
	}

	deviation /oc-line-protect:aps/oc-line-protect:aps-modules/oc-line-protect:aps-module/oc-line-protect:ports/oc-line-protect:common-in/oc-line-protect:state/oc-line-protect:optical-power/oc-line-protect:max {
		deviate add {
			sonic-ext:field-name "max";
		}
	}

	deviation /oc-line-protect:aps/oc-line-protect:aps-modules/oc-line-protect:aps-module/oc-line-protect:ports/oc-line-protect:common-in/oc-line-protect:state/oc-line-protect:optical-power/oc-line-protect:interval {
		deviate add {
			sonic-ext:field-name "interval";
		}
	}

	deviation /oc-line-protect:aps/oc-line-protect:aps-modules/oc-line-protect:aps-module/oc-line-protect:ports/oc-line-protect:common-in/oc-line-protect:state/oc-line-protect:optical-power/oc-line-protect:max-time {
		deviate add {
			sonic-ext:field-name "max-time";
		}
	}

	deviation /oc-line-protect:aps/oc-line-protect:aps-modules/oc-line-protect:aps-module/oc-line-protect:ports/oc-line-protect:common-in/oc-line-protect:state/oc-line-protect:optical-power/oc-line-protect:min-time {
		deviate add {
			sonic-ext:field-name "min-time";
		}
	}

	deviation /oc-line-protect:aps/oc-line-protect:aps-modules/oc-line-protect:aps-module/oc-line-protect:ports/oc-line-protect:common-in/oc-line-protect:state/oc-line-protect:optical-power/oc-line-protect:instant {
		deviate add {
			sonic-ext:field-name "instant";
		}
	}

	deviation /oc-line-protect:aps/oc-line-protect:aps-modules/oc-line-protect:aps-module/oc-line-protect:ports/oc-line-protect:common-in/oc-line-protect:state/oc-line-protect:optical-power/oc-line-protect:avg {
		deviate add {
			sonic-ext:field-name "avg";
		}
	}

	deviation /oc-line-protect:aps/oc-line-protect:aps-modules/oc-line-protect:aps-module/oc-line-protect:ports/oc-line-protect:common-in/oc-line-protect:state/oc-line-protect:enabled {
		deviate add {
			sonic-ext:field-name "enabled";
		}
	}

	deviation /oc-line-protect:aps/oc-line-protect:aps-modules/oc-line-protect:aps-module/oc-line-protect:ports/oc-line-protect:common-in/oc-line-protect:state/oc-line-protect:target-attenuation {
		deviate add {
			sonic-ext:field-name "target-attenuation";
		}
	}

	deviation /oc-line-protect:aps/oc-line-protect:aps-modules/oc-line-protect:aps-module/oc-line-protect:ports/oc-line-protect:common-in/oc-line-protect:state/oc-line-protect:attenuation {
		deviate add {
			sonic-ext:field-name "attenuation";
		}
	}

	deviation /oc-line-protect:aps/oc-line-protect:aps-modules/oc-line-protect:aps-module/oc-line-protect:name {
		deviate add {
		}
	}
}
