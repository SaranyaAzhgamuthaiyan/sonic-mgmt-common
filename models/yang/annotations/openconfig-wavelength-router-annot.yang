module openconfig-wavelength-router-annot {

    yang-version "1";

    namespace "http://openconfig.net/yang/annotation/oc-wave-router-annot";
    prefix "oc-wave-router-annot";

    import openconfig-extensions { prefix oc-ext; }
    import openconfig-platform { prefix oc-platform; }
    import openconfig-transport-types { prefix oc-opt-types; }
    import openconfig-wavelength-router { prefix oc-wave-router; }
    import sonic-extensions { prefix sonic-ext; }

    deviation /oc-wave-router:wavelength-router {
      deviate add {
        sonic-ext:post-transformer "media_channel_post_xfmr";
        sonic-ext:subscribe-on-change "enable";
        sonic-ext:get-namespace "media_channel_get_namespace_xfmr";
      }
    }

    deviation /oc-wave-router:wavelength-router/oc-wave-router:media-channels {
      deviate add {
        sonic-ext:table-name "MEDIA_CHANNEL";
      }
    }

    deviation /oc-wave-router:wavelength-router/oc-wave-router:media-channels/oc-wave-router:channel {
      deviate add {
        sonic-ext:key-transformer "media_channel_key_xfmr";
      }
    }

    deviation /oc-wave-router:wavelength-router/oc-wave-router:media-channels/oc-wave-router:channel/oc-wave-router:index {
      deviate add {
      }
    }

    deviation /oc-wave-router:wavelength-router/oc-wave-router:media-channels/oc-wave-router:channel/oc-wave-router:config {
      deviate add {
      }
    }

    deviation /oc-wave-router:wavelength-router/oc-wave-router:media-channels/oc-wave-router:channel/oc-wave-router:config/oc-wave-router:ase-injection-mode {
      deviate add {
      }
    }

    deviation /oc-wave-router:wavelength-router/oc-wave-router:media-channels/oc-wave-router:channel/oc-wave-router:config/oc-wave-router:lower-frequency {
      deviate add {
         sonic-ext:field-name "lower-frequency";
      }
    }

    deviation /oc-wave-router:wavelength-router/oc-wave-router:media-channels/oc-wave-router:channel/oc-wave-router:config/oc-wave-router:admin-status {
      deviate add {
         sonic-ext:field-name "admin-status";
      }
    }

    deviation /oc-wave-router:wavelength-router/oc-wave-router:media-channels/oc-wave-router:channel/oc-wave-router:config/oc-wave-router:ase-control-mode {
      deviate add {
         sonic-ext:field-name "ase-control-mode";
      }
    }

    deviation /oc-wave-router:wavelength-router/oc-wave-router:media-channels/oc-wave-router:channel/oc-wave-router:config/oc-wave-router:super-channel-parent {
      deviate add {
         sonic-ext:field-name "super-channel-parent";
      }
    }

    deviation /oc-wave-router:wavelength-router/oc-wave-router:media-channels/oc-wave-router:channel/oc-wave-router:config/oc-wave-router:max-undershoot-compensation {
      deviate add {
      }
    }

    deviation /oc-wave-router:wavelength-router/oc-wave-router:media-channels/oc-wave-router:channel/oc-wave-router:config/oc-wave-router:max-overshoot-compensation {
      deviate add {
      }
    }

    deviation /oc-wave-router:wavelength-router/oc-wave-router:media-channels/oc-wave-router:channel/oc-wave-router:config/oc-wave-router:ase-injection-threshold {
      deviate add {
        sonic-ext:field-name "ase-injection-threshold";
      }
    }

    deviation /oc-wave-router:wavelength-router/oc-wave-router:media-channels/oc-wave-router:channel/oc-wave-router:config/oc-wave-router:attenuation-control-mode {
      deviate add {
        sonic-ext:field-name "attenuation-control-mode";
      }
    }

    deviation /oc-wave-router:wavelength-router/oc-wave-router:media-channels/oc-wave-router:channel/oc-wave-router:config/oc-wave-router:index {
      deviate add {
        sonic-ext:field-transformer "media_channel_field_xfmr";
      }
    }

    deviation /oc-wave-router:wavelength-router/oc-wave-router:media-channels/oc-wave-router:channel/oc-wave-router:config/oc-wave-router:super-channel {
      deviate add {
        sonic-ext:field-name "super-channel";
      }
    }

    deviation /oc-wave-router:wavelength-router/oc-wave-router:media-channels/oc-wave-router:channel/oc-wave-router:config/oc-wave-router:media-channel-injection-offset {
      deviate add {
      }
    }

    deviation /oc-wave-router:wavelength-router/oc-wave-router:media-channels/oc-wave-router:channel/oc-wave-router:config/oc-wave-router:upper-frequency {
      deviate add {
        sonic-ext:field-name "upper-frequency";
      }
    }

    deviation /oc-wave-router:wavelength-router/oc-wave-router:media-channels/oc-wave-router:channel/oc-wave-router:config/oc-wave-router:attenuation-control-range {
      deviate add {
      }
    }

    deviation /oc-wave-router:wavelength-router/oc-wave-router:media-channels/oc-wave-router:channel/oc-wave-router:config/oc-wave-router:ase-injection-delta {
      deviate add {
      }
    }

    deviation /oc-wave-router:wavelength-router/oc-wave-router:media-channels/oc-wave-router:channel/oc-wave-router:config/oc-wave-router:name {
    deviate add {
       sonic-ext:field-name "name";
      }
    }

    deviation /oc-wave-router:wavelength-router/oc-wave-router:media-channels/oc-wave-router:channel/oc-wave-router:state {
      deviate add {
        sonic-ext:db-name "STATE_DB";
        sonic-ext:table-name "MEDIA_CHANNEL_TABLE";
        sonic-ext:key-transformer "media_channel_key_xfmr";
     }
    }

    deviation /oc-wave-router:wavelength-router/oc-wave-router:media-channels/oc-wave-router:channel/oc-wave-router:state/oc-wave-router:ase-injection-mode {
      deviate add {
         sonic-ext:field-name "ase-injection-mode";
      }
    }

    deviation /oc-wave-router:wavelength-router/oc-wave-router:media-channels/oc-wave-router:channel/oc-wave-router:state/oc-wave-router:ase-control-mode {
      deviate add {
        sonic-ext:field-name "ase-control-mode";
      }
    }

    deviation /oc-wave-router:wavelength-router/oc-wave-router:media-channels/oc-wave-router:channel/oc-wave-router:state/oc-wave-router:ase-injection-delta {
      deviate add {
        sonic-ext:field-name "ase-injection-delta";
      }
    }

    deviation /oc-wave-router:wavelength-router/oc-wave-router:media-channels/oc-wave-router:channel/oc-wave-router:state/oc-wave-router:attenuation-control-range {
      deviate add {
        sonic-ext:field-name "attenuation-control-range";
      }
    }

    deviation /oc-wave-router:wavelength-router/oc-wave-router:media-channels/oc-wave-router:channel/oc-wave-router:state/oc-wave-router:index {
      deviate add {
         sonic-ext:field-transformer "media_channel_field_xfmr";
      }
    }

    deviation /oc-wave-router:wavelength-router/oc-wave-router:media-channels/oc-wave-router:channel/oc-wave-router:state/oc-wave-router:name {
      deviate add {
        sonic-ext:field-name "name";
      }
    }

    deviation /oc-wave-router:wavelength-router/oc-wave-router:media-channels/oc-wave-router:channel/oc-wave-router:state/oc-wave-router:oper-status {
      deviate add {
        sonic-ext:field-name "oper-status";
      }
    }

    deviation /oc-wave-router:wavelength-router/oc-wave-router:media-channels/oc-wave-router:channel/oc-wave-router:state/oc-wave-router:super-channel {
      deviate add {
        sonic-ext:field-name "super-channel";
      }
    }

    deviation /oc-wave-router:wavelength-router/oc-wave-router:media-channels/oc-wave-router:channel/oc-wave-router:state/oc-wave-router:ase-injection-threshold {
      deviate add {
        sonic-ext:field-name "ase-injection-threshold";
      }
    }

    deviation /oc-wave-router:wavelength-router/oc-wave-router:media-channels/oc-wave-router:channel/oc-wave-router:state/oc-wave-router:media-channel-injection-offset {
      deviate add {
      }
    }

    deviation /oc-wave-router:wavelength-router/oc-wave-router:media-channels/oc-wave-router:channel/oc-wave-router:state/oc-wave-router:max-overshoot-compensation {
      deviate add {
      }
    }

    deviation /oc-wave-router:wavelength-router/oc-wave-router:media-channels/oc-wave-router:channel/oc-wave-router:state/oc-wave-router:ase-status {
      deviate add {
       sonic-ext:field-name "ase-status";
      }
    }

    deviation /oc-wave-router:wavelength-router/oc-wave-router:media-channels/oc-wave-router:channel/oc-wave-router:state/oc-wave-router:max-undershoot-compensation {
      deviate add {
      }
    }

    deviation /oc-wave-router:wavelength-router/oc-wave-router:media-channels/oc-wave-router:channel/oc-wave-router:state/oc-wave-router:lower-frequency {
      deviate add {
        sonic-ext:field-name "lower-frequency";
      }
    }

    deviation /oc-wave-router:wavelength-router/oc-wave-router:media-channels/oc-wave-router:channel/oc-wave-router:state/oc-wave-router:attenuation-control-mode {
      deviate add {
       sonic-ext:field-name "attenuation-control-mode";
      }
    }

    deviation /oc-wave-router:wavelength-router/oc-wave-router:media-channels/oc-wave-router:channel/oc-wave-router:state/oc-wave-router:upper-frequency {
      deviate add {
       sonic-ext:field-name "upper-frequency";
      }
    }

    deviation /oc-wave-router:wavelength-router/oc-wave-router:media-channels/oc-wave-router:channel/oc-wave-router:state/oc-wave-router:super-channel-parent {
      deviate add {
       sonic-ext:field-name "super-channel-parent";
      }
    }

    deviation /oc-wave-router:wavelength-router/oc-wave-router:media-channels/oc-wave-router:channel/oc-wave-router:state/oc-wave-router:admin-status {
      deviate add {
       sonic-ext:field-name "admin-status";
      }
    }
    deviation /oc-wave-router:wavelength-router/oc-wave-router:media-channels/oc-wave-router:channel/oc-wave-router:source {
      deviate add {
       //sonic-ext:table-name "MEDIA_CHANNEL";
      }
    }

    deviation /oc-wave-router:wavelength-router/oc-wave-router:media-channels/oc-wave-router:channel/oc-wave-router:source/oc-wave-router:config {
      deviate add {
      }
    }

    deviation /oc-wave-router:wavelength-router/oc-wave-router:media-channels/oc-wave-router:channel/oc-wave-router:source/oc-wave-router:config/oc-wave-router:port-name {
      deviate add {
        sonic-ext:field-name "source-port-name";
      }
    }

    deviation /oc-wave-router:wavelength-router/oc-wave-router:media-channels/oc-wave-router:channel/oc-wave-router:source/oc-wave-router:state {
      deviate add {
        sonic-ext:db-name "STATE_DB";
        sonic-ext:table-name "MEDIA_CHANNEL_TABLE";
        sonic-ext:key-transformer "media_channel_key_xfmr";
      }
    }

    deviation /oc-wave-router:wavelength-router/oc-wave-router:media-channels/oc-wave-router:channel/oc-wave-router:source/oc-wave-router:state/oc-wave-router:port-name {
      deviate add {
        sonic-ext:field-name "source-port-name";
      }
    }
deviation /oc-wave-router:wavelength-router/oc-wave-router:media-channels/oc-wave-router:channel/oc-wave-router:dest {
      deviate add {
      }
    }

    deviation /oc-wave-router:wavelength-router/oc-wave-router:media-channels/oc-wave-router:channel/oc-wave-router:dest/oc-wave-router:config {
      deviate add {
      }
    }

    deviation /oc-wave-router:wavelength-router/oc-wave-router:media-channels/oc-wave-router:channel/oc-wave-router:dest/oc-wave-router:config/oc-wave-router:port-name {
      deviate add {
       sonic-ext:field-name "dest-port-name";
      }
    }

    deviation /oc-wave-router:wavelength-router/oc-wave-router:media-channels/oc-wave-router:channel/oc-wave-router:dest/oc-wave-router:state {
      deviate add {
        sonic-ext:db-name "STATE_DB";
        sonic-ext:table-name "MEDIA_CHANNEL_TABLE";
        sonic-ext:key-transformer "media_channel_key_xfmr";
      }
    }

    deviation /oc-wave-router:wavelength-router/oc-wave-router:media-channels/oc-wave-router:channel/oc-wave-router:dest/oc-wave-router:state/oc-wave-router:port-name {
      deviate add {
        sonic-ext:field-name "dest-port-name";
        
      }
    }
    deviation /oc-wave-router:wavelength-router/oc-wave-router:media-channels/oc-wave-router:channel/oc-wave-router:spectrum-power-profile {
      deviate add {
      }
    }

    deviation /oc-wave-router:wavelength-router/oc-wave-router:media-channels/oc-wave-router:channel/oc-wave-router:spectrum-power-profile/oc-wave-router:distribution {
      deviate add {
        sonic-ext:table-name "MEDIA_CHANNEL_DISTRIBUTION";
        sonic-ext:key-transformer "media_channel_distribution_key_xfmr";
      }
    }

    deviation /oc-wave-router:wavelength-router/oc-wave-router:media-channels/oc-wave-router:channel/oc-wave-router:spectrum-power-profile/oc-wave-router:distribution/oc-wave-router:lower-frequency {
      deviate add {
      }
    }

    deviation /oc-wave-router:wavelength-router/oc-wave-router:media-channels/oc-wave-router:channel/oc-wave-router:spectrum-power-profile/oc-wave-router:distribution/oc-wave-router:upper-frequency {
      deviate add {
      }
    }

    deviation /oc-wave-router:wavelength-router/oc-wave-router:media-channels/oc-wave-router:channel/oc-wave-router:spectrum-power-profile/oc-wave-router:distribution/oc-wave-router:config {
      deviate add {
      }
    }

    deviation /oc-wave-router:wavelength-router/oc-wave-router:media-channels/oc-wave-router:channel/oc-wave-router:spectrum-power-profile/oc-wave-router:distribution/oc-wave-router:config/oc-wave-router:target-power {
      deviate add {
       sonic-ext:field-name "target-power";
      }
    }

    deviation /oc-wave-router:wavelength-router/oc-wave-router:media-channels/oc-wave-router:channel/oc-wave-router:spectrum-power-profile/oc-wave-router:distribution/oc-wave-router:config/oc-wave-router:lower-frequency {
      deviate add {
        sonic-ext:field-transformer "media_channel_lf_field_xfmr";
      }
    }

    deviation /oc-wave-router:wavelength-router/oc-wave-router:media-channels/oc-wave-router:channel/oc-wave-router:spectrum-power-profile/oc-wave-router:distribution/oc-wave-router:config/oc-wave-router:upper-frequency {
      deviate add {
        sonic-ext:field-transformer "media_channel_uf_field_xfmr";
      }
    }

    deviation /oc-wave-router:wavelength-router/oc-wave-router:media-channels/oc-wave-router:channel/oc-wave-router:spectrum-power-profile/oc-wave-router:distribution/oc-wave-router:state {
      deviate add {
        sonic-ext:db-name "STATE_DB";
        sonic-ext:table-name "MEDIA_CHANNEL_DISTRIBUTION_TABLE";
        sonic-ext:key-transformer "media_channel_distribution_key_xfmr";
      }
    }

    deviation /oc-wave-router:wavelength-router/oc-wave-router:media-channels/oc-wave-router:channel/oc-wave-router:spectrum-power-profile/oc-wave-router:distribution/oc-wave-router:state/oc-wave-router:upper-frequency {
      deviate add {
        sonic-ext:field-transformer "media_channel_uf_field_xfmr";
      }
    }

    deviation /oc-wave-router:wavelength-router/oc-wave-router:media-channels/oc-wave-router:channel/oc-wave-router:spectrum-power-profile/oc-wave-router:distribution/oc-wave-router:state/oc-wave-router:target-power {
      deviate add {
        sonic-ext:field-name "target-power";
      }
    }

    deviation /oc-wave-router:wavelength-router/oc-wave-router:media-channels/oc-wave-router:channel/oc-wave-router:spectrum-power-profile/oc-wave-router:distribution/oc-wave-router:state/oc-wave-router:lower-frequency {
      deviate add {
        sonic-ext:field-transformer "media_channel_lf_field_xfmr";
      }
    }
}
