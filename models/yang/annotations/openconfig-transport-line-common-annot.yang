module openconfig-transport-line-common-annot {

	yang-version "";

	namespace "http://openconfig.net/yang/annotation/oc-line-com-annot";
	prefix "oc-line-com-annot";

	import iana-if-type { prefix ianaift; }
	import openconfig-extensions { prefix oc-ext; }
	import openconfig-interfaces { prefix oc-if; }
	import openconfig-platform { prefix oc-platform; }
	import openconfig-types { prefix oc-types; }
	import openconfig-transport-types { prefix oc-opt-types; }
	import openconfig-platform-transceiver { prefix oc-transceiver; }
	import openconfig-transport-line-common { prefix oc-line-com; }
	import sonic-extensions { prefix sonic-ext; }

	deviation /oc-platform:components/oc-platform:component/oc-platform:port/oc-line-com:optical-port {
		deviate add {
        	}
	}

	deviation /oc-platform:components/oc-platform:component/oc-platform:port/oc-line-com:optical-port/oc-line-com:config {
		deviate add {
		}
	}

	deviation /oc-platform:components/oc-platform:component/oc-platform:port/oc-line-com:optical-port/oc-line-com:config/oc-line-com:admin-state {
		deviate add {
		}
        }

	deviation /oc-platform:components/oc-platform:component/oc-platform:port/oc-line-com:optical-port/oc-line-com:state {
		deviate add {
			sonic-ext:db-name "STATE_DB";
			sonic-ext:table-name "PORT";
			sonic-ext:key-transformer "optical_port_key_xfmr";
                        sonic-ext:get-namespace "optical_port_get_namespace_xfmr";         
		}
	}

	deviation /oc-platform:components/oc-platform:component/oc-platform:port/oc-line-com:optical-port/oc-line-com:state/oc-line-com:admin-state {
		deviate add {
			sonic-ext:field-name "admin-state";
		}
	}

	deviation /oc-platform:components/oc-platform:component/oc-platform:port/oc-line-com:optical-port/oc-line-com:state/oc-line-com:input-power {
		deviate add {
			sonic-ext:db-name "COUNTERS_DB";
			sonic-ext:table-name "PORT";
			sonic-ext:key-transformer "optical_port_input_power_key_xfmr";
		}
	}

	deviation /oc-platform:components/oc-platform:component/oc-platform:port/oc-line-com:optical-port/oc-line-com:state/oc-line-com:input-power/oc-line-com:instant {
		deviate add {
			sonic-ext:field-name "instant";
		}
	}

	deviation /oc-platform:components/oc-platform:component/oc-platform:port/oc-line-com:optical-port/oc-line-com:state/oc-line-com:input-power/oc-line-com:avg {
		deviate add {
			sonic-ext:field-name "avg";
		}
	}

	deviation /oc-platform:components/oc-platform:component/oc-platform:port/oc-line-com:optical-port/oc-line-com:state/oc-line-com:input-power/oc-line-com:min {
		deviate add {
			sonic-ext:field-name "min";
		}
	}

	deviation /oc-platform:components/oc-platform:component/oc-platform:port/oc-line-com:optical-port/oc-line-com:state/oc-line-com:input-power/oc-line-com:max {
		deviate add {
			sonic-ext:field-name "max";
		}
	}

	deviation /oc-platform:components/oc-platform:component/oc-platform:port/oc-line-com:optical-port/oc-line-com:state/oc-line-com:input-power/oc-line-com:interval {
		deviate add {
			sonic-ext:field-name "interval";
		}
	}

	deviation /oc-platform:components/oc-platform:component/oc-platform:port/oc-line-com:optical-port/oc-line-com:state/oc-line-com:input-power/oc-line-com:min-time {
		deviate add {
			sonic-ext:field-name "min-time";
		}
	}

	deviation /oc-platform:components/oc-platform:component/oc-platform:port/oc-line-com:optical-port/oc-line-com:state/oc-line-com:input-power/oc-line-com:max-time {
		deviate add {
			sonic-ext:field-name "max-time";
		}
	}

	deviation /oc-platform:components/oc-platform:component/oc-platform:port/oc-line-com:optical-port/oc-line-com:state/oc-line-com:output-power {
		deviate add {
			sonic-ext:db-name "COUNTERS_DB";
			sonic-ext:table-name "PORT";
			sonic-ext:key-transformer "optical_port_output_power_key_xfmr";
		}
	}

	deviation /oc-platform:components/oc-platform:component/oc-platform:port/oc-line-com:optical-port/oc-line-com:state/oc-line-com:output-power/oc-line-com:instant {
		deviate add {
			sonic-ext:field-name "instant";
		}
	}

	deviation /oc-platform:components/oc-platform:component/oc-platform:port/oc-line-com:optical-port/oc-line-com:state/oc-line-com:output-power/oc-line-com:avg {
		deviate add {
			sonic-ext:field-name "avg";
		}
	}

	deviation /oc-platform:components/oc-platform:component/oc-platform:port/oc-line-com:optical-port/oc-line-com:state/oc-line-com:output-power/oc-line-com:min {
		deviate add {
			sonic-ext:field-name "min";
		}
	}

	deviation /oc-platform:components/oc-platform:component/oc-platform:port/oc-line-com:optical-port/oc-line-com:state/oc-line-com:output-power/oc-line-com:max {
		deviate add {
			sonic-ext:field-name "max";
		}
	}

	deviation /oc-platform:components/oc-platform:component/oc-platform:port/oc-line-com:optical-port/oc-line-com:state/oc-line-com:output-power/oc-line-com:interval {
		deviate add {
			sonic-ext:field-name "interval";
		}
	}

	deviation /oc-platform:components/oc-platform:component/oc-platform:port/oc-line-com:optical-port/oc-line-com:state/oc-line-com:output-power/oc-line-com:min-time {
		deviate add {
			sonic-ext:field-name "min-time";
		}
	}

	deviation /oc-platform:components/oc-platform:component/oc-platform:port/oc-line-com:optical-port/oc-line-com:state/oc-line-com:output-power/oc-line-com:max-time {
		deviate add {
			sonic-ext:field-name "max-time";
		}
	}

	deviation /oc-platform:components/oc-platform:component/oc-platform:port/oc-line-com:optical-port/oc-line-com:state/oc-line-com:optical-port-type {
		deviate add {
			sonic-ext:field-name "optical-port-type";
		}
	}

	deviation /oc-platform:components/oc-platform:component/oc-platform:port/oc-line-com:optical-port/oc-line-com:state/oc-line-com:tilt {
		deviate add {
		}
	}
}
