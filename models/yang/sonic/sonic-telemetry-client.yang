module sonic-telemetry-client {

    yang-version 1.1;

    namespace "http://github.com/sonic-net/sonic-telemetry-client";
    prefix telemetry_client;

    import ietf-inet-types {
        prefix inet;
    }

    organization
        "SONiC";

    contact
        "SONiC";

    description
        "TELEMETRY_CLIENT yang Module for SONiC OS";

    revision 2023-01-12 {
        description
            "First revision";
    }

    typedef report-type {
        type enumeration {
            enum periodic;
            enum stream;
            enum once;
        }
    }
    typedef path_target {
        type enumeration {
            enum APPL_DB;
            enum CONFIG_DB;
            enum COUNTERS_DB;
            enum STATE_DB;
            enum OTHERS;
        }
    }

    typedef encoding {
        type enumeration {
            enum JSON_IETF;
            enum ASCII;
            enum BYTES;
            enum PROTO;
        }
    }

    typedef ipv4-port {
        type string {
            pattern
                '((([0-9]|[1-9][0-9]|1[0-9][0-9]|2[0-4][0-9]|25[0-5])\.){3}'
            +  '([0-9]|[1-9][0-9]|1[0-9][0-9]|2[0-4][0-9]|25[0-5]):'
            +  '([0-9]|[1-9]\d{1,3}|[1-5]\d{1,4}|6[0-4]\d{1,3}|65[0-4]\d{1,2}|655[0-2][0-9]|6553[0-5]),?)+';
        }
      }

    container sonic-telemetry-client{

        container TELEMETRY_CLIENT {

            list TELEMETRY_CLIENT_LIST {
                ordered-by user;
                key "name";

                leaf name {
                    type string;
                }
                leaf report_interval {
                    type uint64;
                    description "report_interval unit ms";
                    default 5000;
                }
                leaf path_target {
                    type string;
                }
                leaf paths {
                    type string;
                }
                leaf heartbeat_interval {
                    type uint64;
                    description "heartbeat_interval unit ms";
                }
                leaf report_type {
                  type report-type;
                }
                leaf dst_group {
                  type string;
                }
                leaf retry_interval {
                    type uint64;
                    description "retry_interval unit s";
                }

                leaf src_ip {
                    type inet:ip-address;
                }

                leaf encoding {
                    type encoding;
                }

                leaf unidirectional {
                    type boolean;
                    default true;
                }
                leaf dst_addr {
                  type string;
                }

           }
        }
    }
}
