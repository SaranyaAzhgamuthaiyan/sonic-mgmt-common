module sonic-telemetry-config {
  yang-version 1.1;

  namespace "http://github.com/Azure/sonic-telemetry-config";
  prefix sonic-tel;

  import sonic-extension {
    prefix sonic-ext;
  }

  import ietf-inet-types {
    prefix inet;
  }

  organization
    "SONiC";
  contact
    "SONiC";
  description
    "SONIC TELEMETRY";

  revision 2024-06-14 {
    description
      "Initial revision.";
  }

  container sonic-telemetry-config {
    container SENSOR_GROUP {
      description
        "Configuration data for telemetry systems in CONFIG_DB.";
      list SENSOR_GROUP_LIST {
        key "sensor-group-id";
        leaf sensor-group-id {
          type string;
          description
            "Name or identifier for the sensor group itself.
             Will be referenced by other configuration specifying a
             sensor group";
        }
        leaf sensor-paths {
          type string;
          description
            "Path to a section of operational state of interest
             (the sensor).";
        }
      }
    }
    container DESTINATION_GROUP {
      description
        "Configuration data for telemetry systems in CONFIG_DB.";
      list DESTINATION_GROUP_LIST {
        key "group-id";
        leaf group-id {
          type string;
          description
            "Unique identifier for the destination group";
        }
      }

    }
    container DESTINATION {
      description
        "Configuration data for telemetry systems in CONFIG_DB.";
      list DESTINATION_LIST {
        key "group-id destination-address destination-port";
        leaf group-id {
          type string;
          description
            "Unique identifier for the destination group";
        }
        leaf destination-address {
          type inet:ip-address;
          description
            "IP address of the telemetry stream destination";
        }
        leaf destination-port {
          type uint16;
          description
            "Protocol (udp or tcp) port number for the telemetry
            stream destination";
        }

      }
    }

    container PERSISTENT_SUBSCRIPTION {
      description
        "Configuration data for telemetry systems in CONFIG_DB.";
      list PERSISTENT_SUBSCRIPTION_LIST {
        key "name";
        leaf name {
          type string;
          description
            "Reference to the identifier of the subscription
            itself. The id will be the handle to refer to the
            subscription once created";
        }

        leaf protocol {
          type string;
          description
            "Selection of the transport protocol for the telemetry
            stream.";
        }
        leaf encoding {
          type string;
          description
            "Selection of the specific encoding or RPC framework
            for telemetry messages to and from the network element.";
        }
      }
    }
    container SENSOR_PROFILE {
      description
        "Configuration data for telemetry systems in CONFIG_DB.";
      list SENSOR_PROFILE_LIST {
        key "name sensor-group";
        leaf name {
          type string;
          description
            "Reference to the identifier of the subscription
            itself. The id will be the handle to refer to the
            subscription once created";
        }

        leaf sensor-group {
          type string;
          description
            "Reference to the sensor group which is used in the profile";
        }
        leaf sample-interval {
          type uint64;
          description
            "Time in milliseconds between the device's sample of a
            telemetry data source. For example, setting this to 100
            would require the local device to collect the telemetry
            data every 100 milliseconds. There can be latency or jitter
            in transmitting the data, but the sample must occur at
            the specified interval.

            The timestamp must reflect the actual time when the data
            was sampled, not simply the previous sample timestamp +
            sample-interval.

            If sample-interval is set to 0, the telemetry sensor
            becomes event based. The sensor must then emit data upon
            every change of the underlying data source.";
        }
        leaf heartbeat-interval {
          type uint64;
          description
            "Maximum time interval in seconds that may pass
            between updates from a device to a telemetry collector.
            If this interval expires, but there is no updated data to
            send (such as if suppress_updates has been configured), the
            device must send a telemetry message to the collector.";
        }
      }
    }
    container SUBSCRIPTION_DESTINATION_GROUP {
      description
        "Configuration data for telemetry systems in CONFIG_DB.";
      list SUBSCRIPTION_DESTINATION_GROUP_LIST {
        key "name group-id";
        leaf name {
          type string;
          description
            "Reference to the identifier of the subscription
            itself. The id will be the handle to refer to the
            subscription once created";
        }

        leaf group-id {
          type string;
          description
            "Unique identifier for the destination group";
        }

      }
    }
  }

}
