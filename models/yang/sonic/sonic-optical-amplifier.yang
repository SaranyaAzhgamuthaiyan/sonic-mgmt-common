module sonic-optical-amplifier {
  namespace "http://github.com/Azure/sonic-optical-amplifier";
  prefix sonic-opt-amp;

  import sonic-extension {
    prefix sonic-ext;
  }

  organization
    "SONiC";
  contact
    "SONiC";
  description
    "SONIC OPTICAL AMPLIFIER";

  revision 2024-03-19 {
    description
      "Initial revision.";
  }

  container sonic-optical-amplifier {
    container AMPLIFIER {
      description
        "Configuration data for optical amplifiers in CONFIG_DB.";
      list AMPLIFIER_LIST {
        key "name";
        leaf name {
          type string;
          description
            "User-defined name assigned to identify a specific amplifier
             in the device";
        }
        leaf type {
          type string;
          description
            "Type of the amplifier";
        }
        leaf target-gain {
          type decimal64 {
            range "0..max";
            fraction-digits 2;
          }
          units "dB";
          description
            "Positive gain applied by the amplifier. This is used
             when the amp-mode is in CONSTANT_GAIN or DYNAMIC_GAIN
             mode to set the target gain that the amplifier should
             achieve.";
        }
        leaf min-gain {
          type decimal64 {
            fraction-digits 2;
          }
          units "dBm";
          description
            "The minimum allowed gain of the amplifier. This is used
             when the amp-mode is in CONSTANT_POWER or DYNAMIC_GAIN mode
             to prevent the gain from dropping below a desired threshold.
             If left empty, the platform will apply a minimum gain based
             on hardware specifications.";
        }
        leaf max-gain {
          type decimal64 {
            fraction-digits 2;
          }
          units "dBm";
          description
            "The maximum allowed gain of the amplifier. This is used
             when the amp-mode is in CONSTANT_POWER or DYNAMIC_GAIN mode
             to prevent the gain from exceeding a desired threshold. If
             left empty, the platform will apply a maximum gain based on
             hardware specifications.";
        }
        leaf target-gain-tilt {
          type decimal64 {
            fraction-digits 2;
          }
          units "dB";
          description
            "Gain tilt control";
        }
        leaf gain-range {
          type string;
          description
            "Selected gain range.  The gain range is a platform-defined
             value indicating the switched gain amplifier setting";
        }
        leaf amp-mode {
          type string;
          description
            "The operating mode of the amplifier";
        }
        leaf target-output-power {
          type decimal64 {
            fraction-digits 2;
          }
          units "dBm";
          description
            "Output optical power of the amplifier.";
        }
        leaf max-output-power {
          type decimal64 {
            fraction-digits 2;
          }
          units "dBm";
          description
            "The maximum optical output power of the amplifier. This
             may be used to prevent the output power from exceeding a
             desired threshold.";
        }
        leaf enabled {
          type boolean;
          description
            "Turns power on / off to the amplifiers gain module.";
        }
        leaf fiber-type-profile {
          type string;
          description
            "The fiber type profile specifies details about the
             fiber type which are needed to accurately determine
             the gain and perform efficient amplification. This is
             only needed for Raman type amplifiers.";
        }
        leaf autolos {
          type boolean;
          description
            "Determines the behavior of the amplifier on input LOS.";
        }
        leaf apr-enabled {
          type boolean;
          description
            "Turns apr on / off to the amplifiers.";
        }
      }
    }

    container OSC {
      description
        "Configuration data for optical amplifiers in CONFIG_DB.";
      list OSC_LIST {
        key "interface";
        leaf interface {
          type string;
          description
            "Reference to an OSC interface";
        }
        leaf enabled {
          type boolean;
          description
            "turn on/off sfp";
        }
      }
    }
  }
}
